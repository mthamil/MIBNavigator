EXTENDED-MADMAN-MIB DEFINITIONS ::= BEGIN

   IMPORTS
       OBJECT-TYPE, enterprises, Counter, Gauge,TimeTicks
	FROM RFC1155-SMI
       DisplayString
	FROM RFC1213-MIB
       applIndex, applName, applOperStatus, applLastChange
	FROM APPLICATION-MIB
       mtaGroupIndex, mtaGroupName, mtaGroupInboundRejectionReason, 
       mtaGroupOutboundConnectFailureReason
	FROM MTA-MIB;

-- OBJECT IDENTIFIERS
   lotus        	OBJECT IDENTIFIER ::= { enterprises 334 }
   notes       	OBJECT IDENTIFIER ::= { lotus 1 }
   lcs         	OBJECT IDENTIFIER ::= { lotus 2 }
   softswitch	OBJECT IDENTIFIER ::= { lotus 3 }
   common-mibs	OBJECT IDENTIFIER ::= { softswitch 1 }
   lms		OBJECT IDENTIFIER ::= { softswitch 2 }

   -- comment this out if using the MODULE-IDENTITY macro
   extendedMADMAN OBJECT IDENTIFIER ::= { common-mibs 1 }     

   TimeInterval ::= INTEGER (0..2147483647)


-- MODULE IDENTIFICATION   use in V2 version only

--extendedMADMAN MODULE-IDENTITY
--       LAST-UPDATED "9511280000Z"
--       ORGANIZATION "Lotus Development Corporation"
--       CONTACT-INFO
--         " Bruce Ernst
--            Postal: 	Lotus Development Corporation
--                 	 640 Lee Road , Suite 200
--	   	Chesterbrook Corporate Center
--                  	Wayne, PA  19087
--                  	US
--
--            Tel: +1 610 251 3404
--            Fax: +1 610 251 3550
--            E-Mail: bge@softsw.ssw.com"
--       DESCRIPTION
--         "The MIB module describing Lotus extensions to MADMAN.
--	  Version 1.0 - first cut - monitoring extensions only. 11/28/94
--	  Version 1.1 - slightly refined 12/14/94
--	  Version 1.2 - downgraded to SNMPV1 due to the lack of V2 8/29/95
--	  Version 1.3 - pared down to minimum support for LMS system manager 8/30/95
--	  Version 1.4 - reviewed version for LMS System Manager 9/11/95
--	 "
--       ::= { common-mibs 1 }

-- APPLICATION LEVEL VARIABLES:
extendedApplTable OBJECT-TYPE
	SYNTAX	SEQUENCE OF ExtendedApplEntry
	ACCESS	not-accessible
	STATUS	mandatory
	DESCRIPTION
	  "The table holding information specific to an Application for which
	  extended information is available."
	::= {extendedMADMAN 1}

extendedApplEntry OBJECT-TYPE
	SYNTAX     ExtendedApplEntry
	ACCESS     not-accessible
	STATUS     mandatory
	DESCRIPTION
	  "The entry associated with each application for which extended information
	  is available."
	INDEX {applIndex}
	::= {extendedApplTable 1}

ExtendedApplEntry ::= SEQUENCE {
	applDescr
	    DisplayString,
	applContact
	    DisplayString,
	applDesiredOperStatus
	    INTEGER
    }

applDescr  OBJECT-TYPE
	SYNTAX    DisplayString
	ACCESS     read-only
	STATUS     mandatory
	DESCRIPTION
	  "A textual description for the application. This should identify the type of 
	  application as well as any other pertinent details regarding its implementation."
	::= {extendedApplEntry 1}

applContact  OBJECT-TYPE
	SYNTAX     DisplayString
	ACCESS     read-only
	STATUS     mandatory
	DESCRIPTION
	  "The textual identification of the contact person for this application, together
	     with information on how to contact that person.."
	::= {extendedApplEntry 2}

applDesiredOperStatus  OBJECT-TYPE
	SYNTAX     INTEGER {
			      up(1),
			      down(2),
			      halted(3)
		   }
	ACCESS     read-write
	STATUS     mandatory
	DESCRIPTION
	  "Indicates the intended operational state of the application
	   	up  	- application is operational and available
	   	down 	- application is not operational
	   	halted 	- application is operational, but not available."
	::= {extendedApplEntry 3}



-- MTA LEVEL VARIABLES:

extendedMtaTable OBJECT-TYPE
	SYNTAX     SEQUENCE OF ExtendedMtaEntry
	ACCESS     not-accessible
	STATUS     mandatory
	DESCRIPTION
	  "The table holding information specific to an MTA for which
	  extended information is available."
	::= {extendedMADMAN 2}

extendedMtaEntry OBJECT-TYPE
	SYNTAX     ExtendedMtaEntry
	ACCESS     not-accessible
	STATUS     mandatory
	DESCRIPTION
	  "The entry associated with each MTA for which extended information
	  is available."
	INDEX {applIndex}
	::= {extendedMtaTable 1}

ExtendedMtaEntry ::= SEQUENCE {
	mtaFailedMessages
	   	Counter,
	mtaFailedVolume
	  	Counter,
       	mtaFailedRecipients
		Counter,
       	mtaLastMessageFailureReason
          		DisplayString,
       	mtaLargestMessageStored
	 	 Gauge,
       	mtaOldestMessageStored
	  	TimeTicks,			
	mtaInputInhibited
		INTEGER,
	mtaType
		INTEGER
    }

mtaFailedMessages OBJECT-TYPE
	SYNTAX     Counter
	ACCESS     read-only
	STATUS     mandatory
	DESCRIPTION
	  "(EMA compliant)  The total number of messages that have 'failed' MTA processing since
	  the MTA was initialized. Possible 'failures' include encode/decode
	  errors, translate errors, unable to route, etc. Protocol/association
	  errors are specifically excluded as they are accounted for in other 
	  MADMAN MIB variables."
	::= {extendedMtaEntry 1}

mtaFailedVolume OBJECT-TYPE
	SYNTAX     Counter
	ACCESS     read-only
	STATUS     mandatory
	DESCRIPTION
	  "(EMA compliant)  The total volume of messages that have 'failed' MTA processing,
	  measured in kilo-octets.  This volume should include all data that
	  is logically above the mail transport level."
	::= {extendedMtaEntry 2}

mtaFailedRecipients OBJECT-TYPE
	SYNTAX     Counter
	ACCESS     read-only
	STATUS     mandatory
	DESCRIPTION
	  "The total number of recipients included in messages that have 'failed'
	  MTA processing since the MTA was initialized."
	::= {extendedMtaEntry 3}

mtaLastMessageFailureReason OBJECT-TYPE
	SYNTAX     DisplayString 
	ACCESS     read-only
	STATUS     mandatory
	DESCRIPTION
	  "The failure reason, if any, for the last message to fail in the MTA.
	  An empty string indicates that the last attempt was successful. If no
	  message has failed since the MTA has been initialized, the value
	  should be 'never'."
	::= {extendedMtaEntry 4}

mtaLargestMessageStored OBJECT-TYPE
	SYNTAX     Gauge
	ACCESS     read-only
	STATUS     mandatory
	DESCRIPTION
	  "(EMA compliant)  The size, in kilo-octets of the largest message currently stored
	   in the MTA."
	::= {extendedMtaEntry 5}

mtaOldestMessageStored OBJECT-TYPE
	SYNTAX     TimeTicks			
	ACCESS     read-only
	STATUS     mandatory
	DESCRIPTION
	  "The time since the oldest message currently stored in the MTA was
	   first safe-stored."
	::= {extendedMtaEntry 6}

mtaInputInhibited OBJECT-TYPE
	SYNTAX     INTEGER {
			true(1),
			false(2)
			}			
	ACCESS     read-write
	STATUS     mandatory
	DESCRIPTION
	  "Indiciates whether or not this MTA is in the 'input inhibited'
	   state, meaning that the MTA will process stored messages, but will
	   not accept new inbound associations."
	::= {extendedMtaEntry 7}

mtaType	OBJECT-TYPE
	SYNTAX     INTEGER {
			x400-92(1),
			x400-88(2),
			x400-84(3),
			smtp-mime(4),
			smtp(5),
			ccMail(6),
			notes(7),
			cmc(8), 
			mapi(9),
			snapi(10),
			snads(11),
			profs(12),
			fax(13),
			other(20),
			unknown(21)
			}			
	ACCESS     read-only
	STATUS     mandatory
	DESCRIPTION
	  "Indiciates the type or primary/native protocol used by this MTA."
	::= {extendedMtaEntry 8}

	
-- MTA GROUP EXTENSION VARIABLES:

extendedMtaGroupTable OBJECT-TYPE
	SYNTAX     SEQUENCE OF ExtendedMtaGroupEntry
	ACCESS     not-accessible
	STATUS     mandatory
	DESCRIPTION
	  "The table holding information specific to each MTA group for which
	  extended information is available."
	::= {extendedMADMAN 3}

extendedMtaGroupEntry OBJECT-TYPE
	SYNTAX     ExtendedMtaGroupEntry
	ACCESS     not-accessible
	STATUS     mandatory
	DESCRIPTION
	  "The entry associated with each MTA group for which extended
	  information is available."
	INDEX {applIndex, mtaGroupIndex}
	::= {extendedMtaGroupTable 1}

ExtendedMtaGroupEntry ::= SEQUENCE {
	mtaGroupIdOfOldestMessage
	  DisplayString,
	mtaGroupLastOutboundAssociationAttempt
	  TimeTicks,	
	mtaGroupMaxInboundAssociations
	  Gauge,
	mtaGroupMaxOutboundAssociations
	  Gauge,
	mtaGroupCurrentState
	  INTEGER,
	mtaGroupLastChange
	  TimeTicks,
	mtaGroupLargestMessageStored
	  INTEGER,
	mtaGroupInboundRejectResourceFailures
	  Counter,
	mtaGroupOutboundFailResourceFailures
	  Counter,
	mtaGroupInboundRejectSecurityViolations
	  Counter,
	mtaGroupOutboundFailSecurityViolations
	  Counter,
	mtaGroupFailedVolume
	  Counter,
	mtaGroupFailedRecipients
	  Counter
    }

mtaGroupIdOfOldestMessage OBJECT-TYPE
	SYNTAX     DisplayString
	ACCESS     read-only
	STATUS     mandatory
	DESCRIPTION
	  "(EMA compliant)  A string representation for the ID of the oldest message stored by this mtaGroup."
	::= {extendedMtaGroupEntry 1}

mtaGroupLastOutboundAssociationAttempt OBJECT-TYPE
	SYNTAX     TimeTicks
	ACCESS     read-only
	STATUS     mandatory
	DESCRIPTION
	  "(EMA compliant)  The value of sysUpTime when this group last attempted an outbound association."
	::= {extendedMtaGroupEntry 2}

mtaGroupMaxInboundAssociations OBJECT-TYPE
	SYNTAX     Gauge
	ACCESS     read-only
	STATUS     mandatory
	DESCRIPTION
	  "The configured or resource-determined maximum number of possible
	  inbound associations available to this group."
	::= {extendedMtaGroupEntry 3}

mtaGroupMaxOutboundAssociations OBJECT-TYPE
	SYNTAX     Gauge
	ACCESS     read-only
	STATUS     mandatory
	DESCRIPTION
	  "The configured or resource-determined maximum number of possible
	  outbound associations available to this group."
	::= {extendedMtaGroupEntry 4}

mtaGroupCurrentState OBJECT-TYPE
        SYNTAX     INTEGER {
         	 		stopped(1),
          			initializing(2),
          			configurable(3),
         			input-disabled(4),
				output-disabled(5),
          			running(6),
	  		stopping(7),
	  		unknown(8)
        }
	ACCESS     read-only
	STATUS     mandatory
	DESCRIPTION
	  "Indicates the internal operational state of the MTA Group.
	   stopped       -  group is not currently active
	   initializing  -  group is in the process of starting
	   configurable  -  group may be configured,but is not processing mail
	   input_disabled - group is running, but not accepting input
	   output_disabled - group is running, but not initiating outbound associations
	   running        -  group is active and processing mail
	   stopping       -  group is in the process of shutting down
	   unknown       -  state does not apply or cannot be determined"
	::= {extendedMtaGroupEntry 5}

mtaGroupLastChange  OBJECT-TYPE
	SYNTAX     TimeTicks
	ACCESS     read-only
	STATUS     mandatory
	DESCRIPTION
	  "The value of sysUpTime at the time this group entered its current
	   operational state."
	::= {extendedMtaGroupEntry 6}

mtaGroupLargestMessageStored OBJECT-TYPE
	SYNTAX     INTEGER
	ACCESS     read-only
	STATUS     mandatory
	DESCRIPTION
	  "The size, in kilo-octets of the largest message currently stored
	   in this group's queue."
	::= {extendedMtaGroupEntry 7}

mtaGroupInboundRejectSecurityViolations OBJECT-TYPE
	SYNTAX     Counter
	ACCESS     read-only
	STATUS     mandatory
	DESCRIPTION
	  "(Potential addition to MADMAN)  The total number of inbound associations to this group that were
	   rejected due to a security violation (incorrect MTA password, etc)."
	::= {extendedMtaGroupEntry 8}

mtaGroupOutboundFailSecurityViolations OBJECT-TYPE
	SYNTAX     Counter
	ACCESS     read-only
	STATUS     mandatory
	DESCRIPTION
	  "(Potential addition to MADMAN)  The total number of outbound associations from this group that
	   failed due to a security violation (incorrect MTA password, etc)."
	::= {extendedMtaGroupEntry 9}

mtaGroupInboundRejectResourceFailures OBJECT-TYPE
	SYNTAX     Counter
	ACCESS     read-only
	STATUS     mandatory
	DESCRIPTION
	  "(Potential addition to MADMAN)  The total number of inbound associations to this group that were
	   rejected due to a lack of resources."
	::= {extendedMtaGroupEntry 10}

mtaGroupOutboundFailResourceFailures OBJECT-TYPE
	SYNTAX     Counter
	ACCESS     read-only
	STATUS     mandatory
	DESCRIPTION
	  "(Potential addition to MADMAN)  The total number of outbound associations from this group that
	   failed due to a lack of resources."
	::= {extendedMtaGroupEntry 11}

mtaGroupFailedVolume OBJECT-TYPE
	SYNTAX     Counter
	ACCESS     read-only
	STATUS     mandatory
	DESCRIPTION
	  "The total volume of messages that have 'failed' group processing,
	  measured in kilo-octets.  This volume should include all data that
	  is logically above the mail transport level."
	::= {extendedMtaGroupEntry 12}

mtaGroupFailedRecipients OBJECT-TYPE
	SYNTAX     Counter
	ACCESS     read-only
	STATUS     mandatory
	DESCRIPTION
	  "The total number of recipients included in messages that have 'failed'
	  group processing since this group was initialized."
	::= {extendedMtaGroupEntry 13}


END
