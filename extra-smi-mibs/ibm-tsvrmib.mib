-- MIB created 11/13/98 22:11:06, by
--   SMIC (the next generation) version 1.6.29, November 22, 1994.

THIN-SERVER-MIB DEFINITIONS ::= BEGIN

-- From file: "tsvrmib.mi2"
-- Compile options "G A T M"

IMPORTS
    Counter32, Integer32, Gauge32, IpAddress
            FROM SNMPv2-SMI-v1
    OBJECT-TYPE
            FROM RFC-1212
    enterprises
            FROM RFC1155-SMI
    TruthValue, DisplayString
            FROM SNMPv2-TC-v1;

ibmThinServer OBJECT IDENTIFIER ::= { enterprises ibm(2) ibmProd(6) ibmIROC(119) ibmIROCsystem(2) 3 }
-- MODULE-IDENTITY
--  LastUpdated
--    9707081200Z
--  OrgName
--    IBM
--  ContactInfo
--    Tracy Fletcher (tracyf @ ralvm29)
--     IBM Corporation
--     800 Park Offices Drive
--     BYQA/664
--     P.O. Box 12195
--     Research Triangle Park, NC 27709, USA
--     Tel:    1 919 254 0061
--     E-mail: tracyf@us.ibm.com
--  Descr
--    MIB for managing thin server function.

genInfo         OBJECT IDENTIFIER ::= { ibmThinServer 1 }
genStat         OBJECT IDENTIFIER ::= { ibmThinServer 2 }
msConnStats     OBJECT IDENTIFIER ::= { ibmThinServer 3 }
rfsStat         OBJECT IDENTIFIER ::= { ibmThinServer 4 }
tftpStat        OBJECT IDENTIFIER ::= { ibmThinServer 5 }
nfsStat         OBJECT IDENTIFIER ::= { ibmThinServer 6 }

thinserverEnable OBJECT-TYPE
    SYNTAX INTEGER {
        disabled(0),
        enabled(1),
        passthru(2),
        disabledpending(3)
        }
    ACCESS read-write
    STATUS mandatory
    DESCRIPTION
        "This device provides thin server support.
         If enabled(1) then this device will provide
         local file caching of selected files. If
         passthru(2) then this device will have connections
         to the clients and pass any frames received on those
         connections to the master server and pass frames
         received from the master server to the appropriate
         client. If disabled(0) then the clients will contact
         the master server directly.  If disabledpending(3),
         then thin server support is in the process of disabling."
    ::= { genInfo 1 }

thinserverRefreshInterval OBJECT-TYPE
    SYNTAX Integer32
--  Units
--    number of days
    ACCESS read-only
    STATUS mandatory
    DESCRIPTION
        "This is the number of days between refreshes
         of this devices cache."
    ::= { genInfo 2 }

thinserverRefreshTime OBJECT-TYPE
    SYNTAX DisplayString
--    Rsyntax OCTET STRING(SIZE(0..255))
    ACCESS read-only
    STATUS mandatory
    DESCRIPTION
        "This is the time of day (12:01:00)
         at which this device will verify that it has
         the same version of the files as the master server,
         and will download any files which are not the
         same version."
    ::= { genInfo 3 }

thinserverRefreshNow OBJECT-TYPE
    SYNTAX INTEGER {
        noaction(1),
        refreshnow(2)
        }
    ACCESS read-write
    STATUS mandatory
    DESCRIPTION
        "This flag indicates that the device
         should immediately refresh all files which
         it is caching.  A read of this object will
         always return noaction(1)."
    ::= { genInfo 4 }

thinserverMemory OBJECT-TYPE
    SYNTAX Integer32
--  Units
--    kilobytes
    ACCESS read-only
    STATUS mandatory
    DESCRIPTION
        "This is the amount of memory in kilobytes
         calculated at runtime to be reserved for caching
         files.  This may be the same amount as the configured
         memory."
    ::= { genInfo 5 }

thinserverHardFileSpace OBJECT-TYPE
    SYNTAX Integer32
--  Units
--    kilobytes
    ACCESS read-only
    STATUS mandatory
    DESCRIPTION
        "This is the total amount of hard file space,
         in kilobytes, which can be used for the files
         being cached for the thin server function."
    ::= { genInfo 6 }

thinserverHardFileUsed OBJECT-TYPE
    SYNTAX Gauge32
--  Units
--    kilobytes
    ACCESS read-only
    STATUS mandatory
    DESCRIPTION
        "This is the total amount of hard file space,
         in kilobytes, which is currently being used
         for the files related to the thin server function."
    ::= { genInfo 7 }

thinserverNumFilesCached OBJECT-TYPE
    SYNTAX Gauge32
    ACCESS read-only
    STATUS mandatory
    DESCRIPTION
        "This is the total number of files being
         cached by the thin server function."
    ::= { genInfo 8 }

thinserverMasterServerIPAddress OBJECT-TYPE
    SYNTAX IpAddress
    ACCESS read-only
    STATUS mandatory
    DESCRIPTION
        "This is the IP address of the server for
         which this device is staging files."
    ::= { genInfo 9 }

thinserverSyncProtocol OBJECT-TYPE
    SYNTAX INTEGER {
        rfs400(1),
        nfs(2)
        }
    ACCESS read-only
    STATUS mandatory
    DESCRIPTION
        "This is the protocol which will be used
         to determine whether or not the cache needs
         to be updated and if so, this protocol will
         be used to retrieve the new version of the
         file(s)."
    ::= { genInfo 10 }

thinserverPreloadListName OBJECT-TYPE
    SYNTAX DisplayString(SIZE(1..255))
--    Rsyntax OCTET STRING(SIZE(1..255))
    ACCESS read-only
    STATUS mandatory
    DESCRIPTION
        "This is the fully-qualified name of the
         file which contains the pre-load list.
         This name can be 1024 bytes long but only
         the last 255 bytes will be displayed."
    ::= { genInfo 11 }

thinserverMountPointsTable OBJECT-TYPE
    SYNTAX SEQUENCE OF ThinserverMountPointsEntry
    ACCESS not-accessible
    STATUS mandatory
    DESCRIPTION
        "When NFS is used as the synchronization protocol,
         then this table lists the directories to be included
         in the mount point from which files will be cached."
    ::= { genInfo 12 }

thinserverMountPointsEntry OBJECT-TYPE
    SYNTAX ThinserverMountPointsEntry
    ACCESS not-accessible
    STATUS mandatory
    DESCRIPTION
        "An entry containing objects
         that define which directories are to
         be included for the mount point."
    INDEX { thinserverMountPointsIndex }
    ::= { thinserverMountPointsTable 1 }

ThinserverMountPointsEntry ::= SEQUENCE {
    thinserverMountPointsIndex Integer32,
    thinserverMountPointsDescr DisplayString,
    thinserverMountPointsScope INTEGER
    }

thinserverMountPointsIndex OBJECT-TYPE
    SYNTAX Integer32
    ACCESS not-accessible
    STATUS mandatory
    DESCRIPTION
        "A unique value for each mount point."
    ::= { thinserverMountPointsEntry 1 }

thinserverMountPointsDescr OBJECT-TYPE
    SYNTAX DisplayString(SIZE(1..255))
--    Rsyntax OCTET STRING(SIZE(1..255))
    ACCESS read-only
    STATUS mandatory
    DESCRIPTION
        "A textual string containing the name
         of a mount point (NFS).  This name can
         be 1024 bytes long, but only the last
         255 bytes will be displayed."
    ::= { thinserverMountPointsEntry 2 }

thinserverMountPointsScope OBJECT-TYPE
    SYNTAX INTEGER {
        include(1),
        exclude(2)
        }
    ACCESS read-only
    STATUS mandatory
    DESCRIPTION
        "If include(1), then that directory is
         included in the mount point.  If exclude(2),
         then that directory is excluded from the
         mount point."
    ::= { thinserverMountPointsEntry 3 }

thinserverPacketTimeout OBJECT-TYPE
    SYNTAX Integer32
--  Units
--    seconds
    ACCESS read-only
    STATUS mandatory
    DESCRIPTION
        "This is the number of seconds defined by the
         user until a packet will time out."
    ::= { genInfo 13 }

thinserverMaxRetries OBJECT-TYPE
    SYNTAX Integer32
    ACCESS read-only
    STATUS mandatory
    DESCRIPTION
        "This is the maximum number of times defined by the
         user that the TFTP daemon will try to resend a packet."
    ::= { genInfo 14 }

thinserverMaxSegSize OBJECT-TYPE
    SYNTAX Integer32
    ACCESS read-only
    STATUS mandatory
    DESCRIPTION
        "This is the maximum segment block size defined by the
         user."
    ::= { genInfo 15 }

thinserverUseHardFile OBJECT-TYPE
    SYNTAX TruthValue
--    Rsyntax INTEGER {
--        true(1),
--        false(2)
--        }
    ACCESS read-only
    STATUS mandatory
    DESCRIPTION
        "This tells whether or not we are to use the hardfile
         when caching."
    ::= { genInfo 16 }

thinserverRestartNow OBJECT-TYPE
    SYNTAX INTEGER {
        noaction(1),
        restartnow(2)
        }
    ACCESS read-write
    STATUS mandatory
    DESCRIPTION
        "This flag indicates that the device
         should immediately restart the thinserver
         feature.  A read of this object will
         always return noaction(1)."
    ::= { genInfo 17 }

thinserverConfiguredMemory OBJECT-TYPE
    SYNTAX Integer32
--  Units
--    kilobytes
    ACCESS read-only
    STATUS mandatory
    DESCRIPTION
        "This is the amount of memory in kilobytes defined
         by the user to be reserved for caching files."
    ::= { genInfo 18 }

thinserverFilesOpenCurrently OBJECT-TYPE
    SYNTAX Gauge32
--  Units
--    files
    ACCESS read-only
    STATUS mandatory
    DESCRIPTION
        "This is the number of files currently
         in the open state because of the thin server
         function."
    ::= { genStat 1 }

thinserverTotalFileOpens OBJECT-TYPE
    SYNTAX Counter32
--  Units
--    files
    ACCESS read-only
    STATUS mandatory
    DESCRIPTION
        "This is the total number of files that have been
         opened since the last reset of the genStat counters
         because of the thin server function."
    ::= { genStat 2 }

thinserverReadMissesDirty OBJECT-TYPE
    SYNTAX Counter32
    ACCESS read-only
    STATUS mandatory
    DESCRIPTION
        "Number of times a read was relayed to the
         server because the file on this device
         is different than the version on the
         master server."
    ::= { genStat 3 }

thinserverReadMissesNotPresent OBJECT-TYPE
    SYNTAX Counter32
    ACCESS read-only
    STATUS mandatory
    DESCRIPTION
        "Number of times a read was relayed to the
         server because this device does not have
         the desired file."
    ::= { genStat 4 }

thinserverOpenFailsFileLocked OBJECT-TYPE
    SYNTAX Counter32
    ACCESS read-only
    STATUS mandatory
    DESCRIPTION
        "Number of times a read was relayed to the
         server because this device cannot serve the
         desired file because it is locked."
    ::= { genStat 5 }

thinserverNoRoomOnHardFile OBJECT-TYPE
    SYNTAX Counter32
    ACCESS read-only
    STATUS mandatory
    DESCRIPTION
        "Number of times the thin server function
         attempted to cache a file but could not
         because there was no more thin server space
         available on the hard disk."
    ::= { genStat 6 }

thinserverResetGenCounters OBJECT-TYPE
    SYNTAX INTEGER {
        noaction(1),
        resetnow(2)
        }
    ACCESS read-write
    STATUS mandatory
    DESCRIPTION
        "Reset the general counters to zero.  A read of
         this object will always return noaction(1)."
    ::= { genStat 7 }

thinserverNumRefreshes OBJECT-TYPE
    SYNTAX Counter32
    ACCESS read-only
    STATUS mandatory
    DESCRIPTION
        "Number of times the cache has been successfully
         refreshed."
    ::= { msConnStats 1 }

thinserverNumRefreshFail OBJECT-TYPE
    SYNTAX Counter32
    ACCESS read-only
    STATUS mandatory
    DESCRIPTION
        "Number of times the cache has failed to refresh
         because the connection to the master server
         could not be established."
    ::= { msConnStats 2 }

thinserverNumFilesRefreshed OBJECT-TYPE
    SYNTAX Counter32
--  Units
--    files
    ACCESS read-only
    STATUS mandatory
    DESCRIPTION
        "Number of files which have been
         refreshed in the cache."
    ::= { msConnStats 3 }

thinserverLastFileUpdate OBJECT-TYPE
    SYNTAX DisplayString
--    Rsyntax OCTET STRING(SIZE(0..255))
    ACCESS read-only
    STATUS mandatory
    DESCRIPTION
        "This is the date and time of day (02/03/1998 23:08:09)
         that the most recent file refresh occurred."
    ::= { msConnStats 4 }

thinserverResetMSConnStats OBJECT-TYPE
    SYNTAX INTEGER {
        noaction(1),
        resetnow(2)
        }
    ACCESS read-write
    STATUS mandatory
    DESCRIPTION
        "Reset the MS connection counters to zero.  A
         read of this object will always return noaction(1)."
    ::= { msConnStats 5 }

thinserverRFSTotalClients OBJECT-TYPE
    SYNTAX Counter32
    ACCESS read-only
    STATUS mandatory
    DESCRIPTION
        "The number of clients which have connected
         to this device using RFS/400 protocol."
    ::= { rfsStat 1 }

thinserverRFSCurrentClients OBJECT-TYPE
    SYNTAX Gauge32
    ACCESS read-only
    STATUS mandatory
    DESCRIPTION
        "The number of clients currently connected
         to this device using RFS/400 protocol."
    ::= { rfsStat 2 }

thinserverRFSFilesServed OBJECT-TYPE
    SYNTAX Counter32
--  Units
--    open requests
    ACCESS read-only
    STATUS mandatory
    DESCRIPTION
        "This is the number of open requests for which
         this device opened a cached file."
    ::= { rfsStat 3 }

thinserverRFSFilesServedByMS OBJECT-TYPE
    SYNTAX Counter32
--  Units
--    open requests
    ACCESS read-only
    STATUS mandatory
    DESCRIPTION
        "This is the number of open requests for which
         this device has passed the request thru to the
         master server because the local copy either
         does not exist, is out-of-date, or is not
         accessable."
    ::= { rfsStat 4 }

thinserverNum449Accepts OBJECT-TYPE
    SYNTAX Counter32
    ACCESS read-only
    STATUS mandatory
    DESCRIPTION
        "The number of port 449 (port mapper) accepts."
    ::= { rfsStat 5 }

thinserverNum449ConnsActive OBJECT-TYPE
    SYNTAX Gauge32
    ACCESS read-only
    STATUS mandatory
    DESCRIPTION
        "The number of port 449 (port mapper) connections
         currently active."
    ::= { rfsStat 6 }

thinserverNum8473Accepts OBJECT-TYPE
    SYNTAX Counter32
    ACCESS read-only
    STATUS mandatory
    DESCRIPTION
        "The number of port 8473 (RFS server) accepts."
    ::= { rfsStat 7 }

thinserverNum8473ConnsActive OBJECT-TYPE
    SYNTAX Gauge32
    ACCESS read-only
    STATUS mandatory
    DESCRIPTION
        "The number of port 8473 (RFS server) connections
         currently active."
    ::= { rfsStat 8 }

thinserverNum8476Accepts OBJECT-TYPE
    SYNTAX Counter32
    ACCESS read-only
    STATUS mandatory
    DESCRIPTION
        "The number of port 8476 (Login server) accepts."
    ::= { rfsStat 9 }

thinserverNum8476ConnsActive OBJECT-TYPE
    SYNTAX Gauge32
    ACCESS read-only
    STATUS mandatory
    DESCRIPTION
        "The number of port 8476 (Login server) connections
         currently active."
    ::= { rfsStat 10 }

thinserverNumRFSWrites OBJECT-TYPE
    SYNTAX Counter32
    ACCESS read-only
    STATUS mandatory
    DESCRIPTION
        "The number of attempts to write to a file being
         cached. The write and all future accesses to
         that file (until it is closed) will be relayed
         to the server."
    ::= { rfsStat 11 }

thinserverResetRFSCounters OBJECT-TYPE
    SYNTAX INTEGER {
        noaction(1),
        resetnow(2)
        }
    ACCESS read-write
    STATUS mandatory
    DESCRIPTION
        "Reset the RFS counters to zero.  A read of
         this object will always return noaction(1)."
    ::= { rfsStat 12 }

thinserverTFTPTotalClients OBJECT-TYPE
    SYNTAX Counter32
    ACCESS read-only
    STATUS mandatory
    DESCRIPTION
        "The number of clients which have connected
         to this device using TFTP protocol."
    ::= { tftpStat 1 }

thinserverTFTPCurrentClients OBJECT-TYPE
    SYNTAX Gauge32
    ACCESS read-only
    STATUS mandatory
    DESCRIPTION
        "The number of clients currently connected
         to this device using TFTP protocol."
    ::= { tftpStat 2 }

thinserverTFTPFileisServed OBJECT-TYPE
    SYNTAX Counter32
--  Units
--    open requests
    ACCESS read-only
    STATUS mandatory
    DESCRIPTION
        "This is the number of open requests for which
         this device opened a cached file."
    ::= { tftpStat 3 }

thinserverTFTPFilesServedByMS OBJECT-TYPE
    SYNTAX Counter32
--  Units
--    open requests
    ACCESS read-only
    STATUS mandatory
    DESCRIPTION
        "This is the number of open requests for which
         this device has passed the request thru to the
         master server because the local copy either
         does not exist, is out-of-date, or is not
         accessable."
    ::= { tftpStat 4 }

thinserverResetTFTPCounters OBJECT-TYPE
    SYNTAX INTEGER {
        noaction(1),
        resetnow(2)
        }
    ACCESS read-write
    STATUS mandatory
    DESCRIPTION
        "Reset the TFTP counters to zero.  A read of
         this object will always return noaction(1)."
    ::= { tftpStat 5 }

thinserverNFSDReadRequests OBJECT-TYPE
    SYNTAX Counter32
    ACCESS read-only
    STATUS mandatory
    DESCRIPTION
        "The total number of READ requests received
         from NFS clients."
    ::= { nfsStat 1 }

thinserverNFSDReadDirRequests OBJECT-TYPE
    SYNTAX Counter32
    ACCESS read-only
    STATUS mandatory
    DESCRIPTION
        "The total number of READDIR requests received
         from NFS clients."
    ::= { nfsStat 2 }

thinserverNFSDUnsupportedRequests OBJECT-TYPE
    SYNTAX Counter32
--  Units
--    open requests
    ACCESS read-only
    STATUS mandatory
    DESCRIPTION
        "This is the total number of requests for
         unsupported procedures received by NFS clients."
    ::= { nfsStat 3 }

thinserverNFSDTotalMounts OBJECT-TYPE
    SYNTAX Counter32
--  Units
--    open requests
    ACCESS read-only
    STATUS mandatory
    DESCRIPTION
        "This is the total number of succesful mount
         requests received from NFS clients."
    ::= { nfsStat 4 }

thinserverNFSDCurrentMounts OBJECT-TYPE
    SYNTAX Gauge32
    ACCESS read-only
    STATUS mandatory
    DESCRIPTION
        "The number of currently active mounts."
    ::= { nfsStat 5 }

thinserverNFSDTotalClients OBJECT-TYPE
    SYNTAX Counter32
    ACCESS read-only
    STATUS mandatory
    DESCRIPTION
        "The total number of clients that have successfully
         mounted to the NFS Server Mount Daemon."
    ::= { nfsStat 6 }

thinserverNFSDCurrentClients OBJECT-TYPE
    SYNTAX Gauge32
    ACCESS read-only
    STATUS mandatory
    DESCRIPTION
        "The current number of clients that have active
         mounts to the NFS Server Mount Daemon."
    ::= { nfsStat 7 }

thinserverNFSDResetCounters OBJECT-TYPE
    SYNTAX INTEGER {
        noaction(1),
        resetnow(2)
        }
    ACCESS read-write
    STATUS mandatory
    DESCRIPTION
        "Reset the NFSD counters to zero.  A read of
         this object will always return noaction(1)."
    ::= { nfsStat 8 }


END
