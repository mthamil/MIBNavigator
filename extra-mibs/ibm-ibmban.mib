-- MIB created 5/06/99 21:04:39, by
--   SMICng version 2.2.06(PRO)(AIX), January 6, 1998. Enterprise key IBM

BOUNDARY-ACCESSS-NODE-MIB DEFINITIONS ::= BEGIN

-- From file: "ibmban.mi2"
-- Compile options "A F G M T"

IMPORTS
    Counter
    enterprises
            FROM RFC1155-SMI
    OBJECT-TYPE
            FROM RFC-1212;

ibmBANMIB OBJECT IDENTIFIER ::= { enterprises ibm(2) ibmProd(6) ibmIROC(119) ibmIROCrouting(4) 12 }
-- MODULE-IDENTITY
--  LastUpdated
--    9808271200Z
--  OrgName
--    IBM
--  ContactInfo
--    Randy Worzella
--     IBM Corporation
--     800 Park Offices Drive
--     FBWA/664
--     P.O. Box 12195
--     Research Triangle Park, NC 27709, USA
--     Tel:    1 919 254 2202
--     E-mail: worzella@us.ibm.com
--  Descr
--    This MIB module contains definitions for the Boundary Access Node
--     function.

ibmBANTable OBJECT-TYPE
    SYNTAX SEQUENCE OF IbmBANEntry
    ACCESS not-accessible
    STATUS mandatory
    DESCRIPTION
        "A table of information related to bridge ports configured
         for Boundary Access Node capability."
    ::= { ibmBANMIB 1 }

ibmBANEntry OBJECT-TYPE
    SYNTAX IbmBANEntry
    ACCESS not-accessible
    STATUS mandatory
    DESCRIPTION
        "Statistics, status and configuration information on a specific
         Boundary Access Node port."
    INDEX { ibmBANbridgePort }
    ::= { ibmBANTable 1 }

IbmBANEntry ::= SEQUENCE {
    ibmBANbridgePort INTEGER,
    ibmBANifIndex INTEGER,
    ibmBANDLCImacAddress OCTET STRING,
    ibmBANboundaryNodeID OCTET STRING,
    ibmBANtype INTEGER,
    ibmBANstatus INTEGER,
    ibmBANinIFrames Counter,
    ibmBANinRRs Counter,
    ibmBANinRNRs Counter,
    ibmBANinRejs Counter,
    ibmBANinTests Counter,
    ibmBANinTestRsps Counter,
    ibmBANinXIDs Counter,
    ibmBANinXIDRsps Counter,
    ibmBANinSABMEs Counter,
    ibmBANinUAs Counter,
    ibmBANinDMs Counter,
    ibmBANinDISCs Counter,
    ibmBANinFRMRs Counter,
    ibmBANinOthers Counter,
    ibmBANoutIFrames Counter,
    ibmBANoutRRs Counter,
    ibmBANoutRNRs Counter,
    ibmBANoutRejs Counter,
    ibmBANoutTests Counter,
    ibmBANoutTestRsps Counter,
    ibmBANoutXIDs Counter,
    ibmBANoutXIDRsps Counter,
    ibmBANoutSABMEs Counter,
    ibmBANoutUAs Counter,
    ibmBANoutDMs Counter,
    ibmBANoutDISCs Counter,
    ibmBANoutFRMRs Counter,
    ibmBANoutOthers Counter
    }

ibmBANbridgePort OBJECT-TYPE
    SYNTAX INTEGER(0..2147483647)
    ACCESS not-accessible
    STATUS mandatory
    DESCRIPTION
        "The BAN bridge port number. It is the same value as the bridge
         MIBs dot1dBasePort."
    ::= { ibmBANEntry 1 }

ibmBANifIndex OBJECT-TYPE
    SYNTAX INTEGER
    ACCESS read-only
    STATUS mandatory
    DESCRIPTION
        "The interface index identifying the physical interface this
         bridge port is assicated with. It is the same value as
         mib-2 ifIndex."
    ::= { ibmBANEntry 2 }

ibmBANDLCImacAddress OBJECT-TYPE
    SYNTAX OCTET STRING(SIZE(6))
    ACCESS read-only
    STATUS mandatory
    DESCRIPTION
        "The MAC address of the frame relay DLCI."
    ::= { ibmBANEntry 3 }

ibmBANboundaryNodeID OBJECT-TYPE
    SYNTAX OCTET STRING(SIZE(6))
    ACCESS read-only
    STATUS mandatory
    DESCRIPTION
        "The boundary node identifier for the SNA node."
    ::= { ibmBANEntry 4 }

ibmBANtype OBJECT-TYPE
    SYNTAX INTEGER {
        bridged(1),
        dlswTerminated(2)
        }
    ACCESS read-only
    STATUS mandatory
    DESCRIPTION
        "An indication whether this port is bridged or DLSw terminated."
    ::= { ibmBANEntry 5 }

ibmBANstatus OBJECT-TYPE
    SYNTAX INTEGER {
        up(1),
        down(2),
        initFail(3)
        }
    ACCESS read-only
    STATUS mandatory
    DESCRIPTION
        "The status of the ban port with the following values:
          up(1)       - FR DLCI up and running as intended
          down(2)     - FR DLCI is not running
          initFail(3) - A configuration problem exists"
    ::= { ibmBANEntry 6 }

ibmBANinIFrames OBJECT-TYPE
    SYNTAX Counter
    ACCESS read-only
    STATUS mandatory
    DESCRIPTION
        "Count of received I-frames."
    ::= { ibmBANEntry 7 }

ibmBANinRRs OBJECT-TYPE
    SYNTAX Counter
    ACCESS read-only
    STATUS mandatory
    DESCRIPTION
        "Count of received RRs."
    ::= { ibmBANEntry 8 }

ibmBANinRNRs OBJECT-TYPE
    SYNTAX Counter
    ACCESS read-only
    STATUS mandatory
    DESCRIPTION
        "Count of received RNRs."
    ::= { ibmBANEntry 9 }

ibmBANinRejs OBJECT-TYPE
    SYNTAX Counter
    ACCESS read-only
    STATUS mandatory
    DESCRIPTION
        "Count of received frame rejects."
    ::= { ibmBANEntry 10 }

ibmBANinTests OBJECT-TYPE
    SYNTAX Counter
    ACCESS read-only
    STATUS mandatory
    DESCRIPTION
        "Count of received TESTs."
    ::= { ibmBANEntry 11 }

ibmBANinTestRsps OBJECT-TYPE
    SYNTAX Counter
    ACCESS read-only
    STATUS mandatory
    DESCRIPTION
        "Count of received TEST responses."
    ::= { ibmBANEntry 12 }

ibmBANinXIDs OBJECT-TYPE
    SYNTAX Counter
    ACCESS read-only
    STATUS mandatory
    DESCRIPTION
        "Count of received XIDs."
    ::= { ibmBANEntry 13 }

ibmBANinXIDRsps OBJECT-TYPE
    SYNTAX Counter
    ACCESS read-only
    STATUS mandatory
    DESCRIPTION
        "Count of received XID responses."
    ::= { ibmBANEntry 14 }

ibmBANinSABMEs OBJECT-TYPE
    SYNTAX Counter
    ACCESS read-only
    STATUS mandatory
    DESCRIPTION
        "Count of received SABMEs."
    ::= { ibmBANEntry 15 }

ibmBANinUAs OBJECT-TYPE
    SYNTAX Counter
    ACCESS read-only
    STATUS mandatory
    DESCRIPTION
        "Count of received UAs."
    ::= { ibmBANEntry 16 }

ibmBANinDMs OBJECT-TYPE
    SYNTAX Counter
    ACCESS read-only
    STATUS mandatory
    DESCRIPTION
        "Count of received DMs."
    ::= { ibmBANEntry 17 }

ibmBANinDISCs OBJECT-TYPE
    SYNTAX Counter
    ACCESS read-only
    STATUS mandatory
    DESCRIPTION
        "Count of received DISCs."
    ::= { ibmBANEntry 18 }

ibmBANinFRMRs OBJECT-TYPE
    SYNTAX Counter
    ACCESS read-only
    STATUS mandatory
    DESCRIPTION
        "Count of received FRMRs."
    ::= { ibmBANEntry 19 }

ibmBANinOthers OBJECT-TYPE
    SYNTAX Counter
    ACCESS read-only
    STATUS mandatory
    DESCRIPTION
        "Count of other packets not counted by the other incoming
         counters."
    ::= { ibmBANEntry 20 }

ibmBANoutIFrames OBJECT-TYPE
    SYNTAX Counter
    ACCESS read-only
    STATUS mandatory
    DESCRIPTION
        "Count of transmitted I-frames."
    ::= { ibmBANEntry 21 }

ibmBANoutRRs OBJECT-TYPE
    SYNTAX Counter
    ACCESS read-only
    STATUS mandatory
    DESCRIPTION
        "Count of transmitted RRs."
    ::= { ibmBANEntry 22 }

ibmBANoutRNRs OBJECT-TYPE
    SYNTAX Counter
    ACCESS read-only
    STATUS mandatory
    DESCRIPTION
        "Count of transmitted RNRs."
    ::= { ibmBANEntry 23 }

ibmBANoutRejs OBJECT-TYPE
    SYNTAX Counter
    ACCESS read-only
    STATUS mandatory
    DESCRIPTION
        "Count of transmitted frame rejects."
    ::= { ibmBANEntry 24 }

ibmBANoutTests OBJECT-TYPE
    SYNTAX Counter
    ACCESS read-only
    STATUS mandatory
    DESCRIPTION
        "Count of transmitted TESTs."
    ::= { ibmBANEntry 25 }

ibmBANoutTestRsps OBJECT-TYPE
    SYNTAX Counter
    ACCESS read-only
    STATUS mandatory
    DESCRIPTION
        "Count of transmitted TEST responses."
    ::= { ibmBANEntry 26 }

ibmBANoutXIDs OBJECT-TYPE
    SYNTAX Counter
    ACCESS read-only
    STATUS mandatory
    DESCRIPTION
        "Count of transmitted XIDs."
    ::= { ibmBANEntry 27 }

ibmBANoutXIDRsps OBJECT-TYPE
    SYNTAX Counter
    ACCESS read-only
    STATUS mandatory
    DESCRIPTION
        "Count of transmitted XID responses."
    ::= { ibmBANEntry 28 }

ibmBANoutSABMEs OBJECT-TYPE
    SYNTAX Counter
    ACCESS read-only
    STATUS mandatory
    DESCRIPTION
        "Count of transmitted SABMEs."
    ::= { ibmBANEntry 29 }

ibmBANoutUAs OBJECT-TYPE
    SYNTAX Counter
    ACCESS read-only
    STATUS mandatory
    DESCRIPTION
        "Count of transmitted UAs."
    ::= { ibmBANEntry 30 }

ibmBANoutDMs OBJECT-TYPE
    SYNTAX Counter
    ACCESS read-only
    STATUS mandatory
    DESCRIPTION
        "Count of transmitted DMs."
    ::= { ibmBANEntry 31 }

ibmBANoutDISCs OBJECT-TYPE
    SYNTAX Counter
    ACCESS read-only
    STATUS mandatory
    DESCRIPTION
        "Count of transmitted DISCs."
    ::= { ibmBANEntry 32 }

ibmBANoutFRMRs OBJECT-TYPE
    SYNTAX Counter
    ACCESS read-only
    STATUS mandatory
    DESCRIPTION
        "Count of transmitted FRMRs."
    ::= { ibmBANEntry 33 }

ibmBANoutOthers OBJECT-TYPE
    SYNTAX Counter
    ACCESS read-only
    STATUS mandatory
    DESCRIPTION
        "Count of other packets not counted by the other outgoing
         counters."
    ::= { ibmBANEntry 34 }


END
