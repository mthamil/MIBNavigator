-- ****************************************************************************
--
--                   Compaq Server Health Features
--         Management Information Base for SNMP Network Management
--
--      Copyright 1992-2001, Compaq Computer Corporation.
--      All Rights Reserved.
--
--      The information in this document is subject to change without notice
--
--      COMPAQ COMPUTER CORPORATION SHALL NOT BE LIABLE FOR TECHNICAL
--      OR EDITORIAL ERRORS OR OMISSIONS CONATINED HEREIN; NOR FOR INCIDENTAL
--      OR CONSEQUENTIAL DAMAGES RESULTING FROM THE FURNISHING, PERFORMANCE,
--      OR USE OF THIS MATERIAL.
--
--      Refer to the READMIB.RDM file for more information about the
--      organization of the information in the Compaq Enterprise.
--
--      The Compaq Enterprise number is 232.
--      The ASN.1 prefix to, and including the Compaq Enterprise is:
--           1.3.6.1.4.1.232
--
-- ****************************************************************************

CPQHLTH-MIB DEFINITIONS ::= BEGIN

    IMPORTS
        compaq                  FROM CPQHOST-MIB
        enterprises             FROM RFC1155-SMI
        Counter                 FROM RFC1155-SMI
        DisplayString           FROM RFC1213-MIB
        OBJECT-TYPE             FROM RFC-1212
        TRAP-TYPE               FROM RFC-1215
        sysName                 FROM RFC1213-MIB
        cpqHoTrapFlags          FROM CPQHOST-MIB
        cpqSiServerSystemId     FROM CPQSINFO-MIB;

--  compaq                  OBJECT IDENTIFIER ::= { enterprises 232 }
    cpqHealth               OBJECT IDENTIFIER ::= { compaq 6 }
    cpqHeMibRev             OBJECT IDENTIFIER ::= { cpqHealth 1 }
    cpqHeComponent          OBJECT IDENTIFIER ::= { cpqHealth 2 }
    cpqHeTrap               OBJECT IDENTIFIER ::= { cpqHealth 3 }

    cpqHeInterface          OBJECT IDENTIFIER ::= { cpqHeComponent 1 }
    cpqHeCriticalError      OBJECT IDENTIFIER ::= { cpqHeComponent 2 }
    cpqHeCorrectableMemory  OBJECT IDENTIFIER ::= { cpqHeComponent 3 }
    cpqHeAsr                OBJECT IDENTIFIER ::= { cpqHeComponent 5 }
    cpqHeThermal            OBJECT IDENTIFIER ::= { cpqHeComponent 6 }
    cpqHePostMsg            OBJECT IDENTIFIER ::= { cpqHeComponent 7 }
    cpqHeSysUtil            OBJECT IDENTIFIER ::= { cpqHeComponent 8 }
    cpqHeFltTolPwrSupply    OBJECT IDENTIFIER ::= { cpqHeComponent 9 }
    cpqHeIRC                OBJECT IDENTIFIER ::= { cpqHeComponent 10 }
    cpqHeEventLog           OBJECT IDENTIFIER ::= { cpqHeComponent 11 }
    cpqHeMgmtDisplay        OBJECT IDENTIFIER ::= { cpqHeComponent 12 }
    cpqHePowerConverter     OBJECT IDENTIFIER ::= { cpqHeComponent 13 }
    cpqHeResilientMemory    OBJECT IDENTIFIER ::= { cpqHeComponent 14 }

    cpqHeOsNetWare3x        OBJECT IDENTIFIER ::= { cpqHeInterface 1 }
    cpqHeOsCommon           OBJECT IDENTIFIER ::= { cpqHeInterface 4 }

-- ****************************************************************************
--   Health MIB Revision
--   ===================
--
-- The compaq enterprise               (1.3.6.1.4.1.232)
--      cpqHealth Group                (1.3.6.1.4.1.232.6)
--       cpqHeMibRev Group             (1.3.6.1.4.1.232.6.1)
--
--     An Insight Agent conforming to this document will return a
--     cpqHeMibRevMajor of one (1) and a cpqHeMibRevMinor of thirteen (13).
--
--
--    Implementation of the MibRev group is mandatory for all agents
--    supporting the Compaq Health MIB.
--
-- ****************************************************************************

    cpqHeMibRevMajor OBJECT-TYPE
        SYNTAX  INTEGER (1..65535)
        ACCESS  read-only
        STATUS  mandatory
        DESCRIPTION
            "The Major Revision level of the MIB.

            A change in the major revision level represents a major change
            in the architecture of the MIB.  A change in the major revision
            level may indicate a significant change in the information
            supported and/or the meaning of the supported information,
            correct interpretation of data may require a MIB document with
            the same major revision level."
        ::= { cpqHeMibRev 1 }

    cpqHeMibRevMinor OBJECT-TYPE
        SYNTAX  INTEGER (0..65535)
        ACCESS  read-only
        STATUS  mandatory
        DESCRIPTION
            "The minor revision level of the MIB.

            A change in the minor revision level may represent some minor
            additional support, no changes to any pre-existing information
            has occurred."
        ::= { cpqHeMibRev 2 }

    cpqHeMibCondition OBJECT-TYPE
        SYNTAX  INTEGER {
            other(1),
            ok(2),              -- default
            degraded(3),
            failed(4)
            }
        ACCESS  read-only
        STATUS  mandatory
        DESCRIPTION
            "The overall condition.

             This object represents the overall status of the server health
             system represented by this MIB."
        ::= { cpqHeMibRev 3 }

-- ****************************************************************************
--   Health MIB NetWare OS Group
--   ===========================
--
-- The compaq enterprise               (1.3.6.1.4.1.232)
--      cpqHealth Group                (1.3.6.1.4.1.232.6)
--       cpqHeComponent Group          (1.3.6.1.4.1.232.6.2)
--        cpqHeInterface Group         (1.3.6.1.4.1.232.6.2.1)
--         cpqHeOsNetWare3x Group      (1.3.6.1.4.1.232.6.2.1.1)
--
--  Implementation of the cpqHeOsNetWare3x group is mandatory for all
--  agents that support the Compaq Server Health MIB in a NetWare host
--  operating environment.
--
-- ****************************************************************************

    cpqHeNw3xDriverName OBJECT-TYPE
        SYNTAX  DisplayString (SIZE (0..255))
        ACCESS  read-only
        STATUS  deprecated
        DESCRIPTION
            "Driver Name.

            This value identifies the NetWare Loadable Module providing the
            operating system access to the Compaq Server Health information."
        ::= { cpqHeOsNetWare3x 1 }

    cpqHeNw3xDriverDate OBJECT-TYPE
        SYNTAX  DisplayString (SIZE (8))
        ACCESS  read-only
        STATUS  deprecated
        DESCRIPTION
            "Driver Date.

            The date of the NetWare Loadable Module providing the operating
            system access to the Compaq Server Health logs.  The date is
            provided in mm/dd/yy format."
        ::= { cpqHeOsNetWare3x 2 }

    cpqHeNw3xDriverVersion OBJECT-TYPE
        SYNTAX  DisplayString (SIZE (0..5))
        ACCESS  read-only
        STATUS  deprecated
        DESCRIPTION
            "Driver Version.

            This is the version of the NetWare Loadable Module (NLM)
            providing the operating system access to the Compaq Server
            Health logs."
        ::= { cpqHeOsNetWare3x 3 }

-- ****************************************************************************
--   Health MIB OS Common Group
--   ==========================
--
-- The compaq enterprise               (1.3.6.1.4.1.232)
--      cpqHealth Group                (1.3.6.1.4.1.232.6)
--       cpqHeComponent Group          (1.3.6.1.4.1.232.6.2)
--        cpqHeInterface Group         (1.3.6.1.4.1.232.6.2.1)
--         cpqHeOsCommon Group         (1.3.6.1.4.1.232.6.2.1.4)
--
--  The cpqHeOsCommon group describes the interface to the Compaq Server
--  health components.  This information describes the interface modules
--  and general OS interface architectural information.
--
--  Implementation of the cpqHeOsCommon group is mandatory for all
--  agents that support the Server Health MIB.
--
-- ****************************************************************************

    cpqHeOsCommonPollFreq OBJECT-TYPE
        SYNTAX  INTEGER (0..65535)
        ACCESS  read-write
        STATUS  mandatory
        DESCRIPTION
            "The Insight Agent's polling frequency.

            The frequency, in seconds, at which the Insight Agent requests
            information from the device driver.  A frequency of zero
            indicates that the Insight Agent retrieves the information upon
            request of a management station, it does not poll the device
            driver at a specific interval.

            If the poll frequency is 0 all attempts to write to this
            object will fail.  If the poll frequency is non-zero,
            setting this value will change the polling frequency of the
            Insight Agent.  Setting the poll frequency to zero will always
            fail, an agent may also choose to fail any request to change
            the poll frequency to a value that would severely impact system
            performance."
        ::= { cpqHeOsCommon 1 }

-- ****************************************************************************
--   Health MIB OS Common Module Table
--   =================================
--
-- The compaq enterprise               (1.3.6.1.4.1.232)
--      cpqHealth Group                (1.3.6.1.4.1.232.6)
--       cpqHeComponent Group          (1.3.6.1.4.1.232.6.2)
--        cpqHeInterface Group         (1.3.6.1.4.1.232.6.2.1)
--         cpqHeOsCommon Group         (1.3.6.1.4.1.232.6.2.1.4)
--           cpqHeOsCommonModuleTable  (1.3.6.1.4.1.232.6.2.1.4.2) deprecated
--
-- ****************************************************************************

    cpqHeOsCommonModuleTable OBJECT-TYPE
        SYNTAX  SEQUENCE OF CpqHeOsCommonModuleEntry
        ACCESS  not-accessible
        STATUS  deprecated
        DESCRIPTION
            "Supporting software table.

             This is a table of software modules that provide an interface
             to the device this server health MIB describes."
        ::= { cpqHeOsCommon 2 }

    cpqHeOsCommonModuleEntry OBJECT-TYPE
        SYNTAX  CpqHeOsCommonModuleEntry
        ACCESS  not-accessible
        STATUS  deprecated
        DESCRIPTION
            "A description of a software modules that provide an interface
            to the device this MIB describes."
        INDEX   { cpqHeOsCommonModuleIndex }
        ::= { cpqHeOsCommonModuleTable 1 }

        CpqHeOsCommonModuleEntry ::= SEQUENCE {
            cpqHeOsCommonModuleIndex       INTEGER,
            cpqHeOsCommonModuleName        DisplayString,
            cpqHeOsCommonModuleVersion     DisplayString,
            cpqHeOsCommonModuleDate        OCTET STRING,
            cpqHeOsCommonModulePurpose     DisplayString
        }

    cpqHeOsCommonModuleIndex OBJECT-TYPE
        SYNTAX  INTEGER (0..255)
        ACCESS  read-only
        STATUS  deprecated
        DESCRIPTION
            "A unique index for this module description."
        ::= { cpqHeOsCommonModuleEntry 1 }

    cpqHeOsCommonModuleName OBJECT-TYPE
        SYNTAX  DisplayString (SIZE (0..255))
        ACCESS  read-only
        STATUS  deprecated
        DESCRIPTION
            "The module name."
        ::= { cpqHeOsCommonModuleEntry 2 }

    cpqHeOsCommonModuleVersion OBJECT-TYPE
        SYNTAX  DisplayString (SIZE (0..5))
        ACCESS  read-only
        STATUS  deprecated
        DESCRIPTION
            "The module version in XX.YY format.

            Where XX is the major version number and YY is the minor version
            number.  This field will be null (size 0) string if the agent
            cannot provide the module version."
        ::= { cpqHeOsCommonModuleEntry 3 }

    cpqHeOsCommonModuleDate OBJECT-TYPE
        SYNTAX  OCTET STRING (SIZE (7))
        ACCESS  read-only
        STATUS  deprecated
        DESCRIPTION
            "The module date.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant.  The year field is set
            with the most significant octet first."
        ::= { cpqHeOsCommonModuleEntry 4 }

    cpqHeOsCommonModulePurpose OBJECT-TYPE
        SYNTAX  DisplayString (SIZE (0..255))
        ACCESS  read-only
        STATUS  deprecated
        DESCRIPTION
            "The purpose of the module described in this entry."
        ::= { cpqHeOsCommonModuleEntry 5 }

-- ****************************************************************************
--   Health MIB Critical Error Group
--   ===============================
--
-- The compaq enterprise               (1.3.6.1.4.1.232)
--      cpqHealth Group                (1.3.6.1.4.1.232.6)
--       cpqHeComponent Group          (1.3.6.1.4.1.232.6.2)
--        cpqHeCriticalError Group     (1.3.6.1.4.1.232.6.2.2)
--
--  The cpqHeCriticalError group describes the health critical error log.
--
--  Implementation of the cpqHeCriticalError group is mandatory for all
--  agents that support the Compaq Health MIB.
--
-- ****************************************************************************

    cpqHeCritLogSupported OBJECT-TYPE
        SYNTAX  INTEGER {
            other(1),
            notSupported(2),
            supported(3)
            }
        ACCESS  read-only
        STATUS  mandatory
        DESCRIPTION
            "This value specifies if this system supports the critical
            error logging feature."
        ::= { cpqHeCriticalError 1 }

    cpqHeCritLogCondition OBJECT-TYPE
        SYNTAX  INTEGER {
            other(1),
            ok(2),
            degraded(3),
            failed(4)
            }
        ACCESS  read-only
        STATUS  mandatory
        DESCRIPTION
            "This value specifies the overall condition of the critical
            error log feature."
        ::= { cpqHeCriticalError 2 }

    cpqHeLastCritErrorAbendMsg OBJECT-TYPE
        SYNTAX  DisplayString (SIZE (0..255))
        ACCESS  read-only
        STATUS  mandatory
        DESCRIPTION
            "Last Critical Termination message.

             The message associated with the last critical error of
             type criticalException(14) or abend(27)."
        ::= { cpqHeCriticalError 3 }

-- ****************************************************************************
--   Health MIB Critical Error Table
--   ===============================
--
-- The compaq enterprise               (1.3.6.1.4.1.232)
--      cpqHealth Group                (1.3.6.1.4.1.232.6)
--       cpqHeComponent Group          (1.3.6.1.4.1.232.6.2)
--        cpqHeCriticalError Group     (1.3.6.1.4.1.232.6.2.2)
--         cpqHeCriticalErrorTable     (1.3.6.1.4.1.232.6.2.2.4)
--
-- ****************************************************************************

    cpqHeCriticalErrorTable OBJECT-TYPE
        SYNTAX  SEQUENCE OF CpqHeCriticalErrorEntry
        ACCESS  not-accessible
        STATUS  mandatory
        DESCRIPTION
            "A table of critical error descriptions."
        ::= { cpqHeCriticalError 4 }

    cpqHeCriticalErrorEntry OBJECT-TYPE
        SYNTAX  CpqHeCriticalErrorEntry
        ACCESS  not-accessible
        STATUS  mandatory
        DESCRIPTION
            "A critical error description."
        INDEX   { cpqHeCriticalErrorIndex }
        ::= { cpqHeCriticalErrorTable 1 }

    CpqHeCriticalErrorEntry ::= SEQUENCE {
        cpqHeCriticalErrorIndex          INTEGER,
        cpqHeCriticalErrorStatus         INTEGER,
        cpqHeCriticalErrorType           INTEGER,
        cpqHeCriticalErrorTime           OCTET STRING,
        cpqHeCriticalErrorInfo           OCTET STRING,
        cpqHeCriticalErrorDesc           DisplayString
    }

    cpqHeCriticalErrorIndex OBJECT-TYPE
        SYNTAX  INTEGER (0..65535)
        ACCESS  read-only
        STATUS  mandatory
        DESCRIPTION
            "A number that uniquely specifies this critical error
            description.  The entries will be in order of occurrence
            with the most recent entry first."
        ::= { cpqHeCriticalErrorEntry 1 }

    cpqHeCriticalErrorStatus OBJECT-TYPE
        SYNTAX  INTEGER {
            uncorrected(1),
            corrected(2)
            }
        ACCESS  read-write
        STATUS  mandatory
        DESCRIPTION
            "This value specifies if the user has marked this error as
            corrected.  Marking errors as corrected may be performed with
            the Compaq Diagnostics or by a set operation on this variable.
            Attempting to set this variable to uncorrected(1) will fail."
        ::= { cpqHeCriticalErrorEntry 2 }

    cpqHeCriticalErrorType OBJECT-TYPE
        SYNTAX  INTEGER {
            other(1),
            empty(2),
            nonCorrectableMemErr(3),
            busMasterTimeoutNmi(4),
            commandBusTimeoutNmi(5),
            ioCheckNmi(6),
            refreshOverflowNmi(7),
            cacheParityNmi(8),
            processorParityNmi(9),
            eisaHostMemReadHit(10),
            processorFailure(11),
            cautionTemperature(12),
            postCriticalError(13),
            criticalException(14),
            serverManagerIfFail(15),
            pentiumIperr(16),
            pentiumAperr(17),
            pentiumIeerr(18),
            pentiumApcheck(19),
            cpuLocalError(20),
            failsafeTimer(21),
            softwareNmi(22),
            asrBaseMemoryParity(23),
            asrExtendedMemParity(24),
            asrResetLimit(25),
            asrMemoryParity(26),
            abend(27),
            asrTestEvent(28),
            asrTimeoutNmi(29),
            fanFailure(30),
            upsDetectedLineFail(31),
            asrDetectedAtBoot(32),
            redunPowerSupplyFailure(33),
            pciBusParityError(34),
            diagnosticError(35),
            rtcChipBatteryFailure(36),
            pentiumBerr(37),
            dcConverterFailure(38),
            cpuInternalThreshPassed(39)
            }
        ACCESS  read-only
        STATUS  mandatory
        DESCRIPTION
            "This value specifies the type of error."
        ::= { cpqHeCriticalErrorEntry 3 }

    cpqHeCriticalErrorTime OBJECT-TYPE
        SYNTAX  OCTET STRING (SIZE (0..3))
        ACCESS  read-only
        STATUS  mandatory
        DESCRIPTION
            "The time of the error: hour (first five bits), day of month
            (next 5 bits), month (next 4 bits), year of the current century
            (next 7 bits).  The last 3 bits are reserved."
        ::= { cpqHeCriticalErrorEntry 4 }

    cpqHeCriticalErrorInfo OBJECT-TYPE
        SYNTAX  OCTET STRING (SIZE (0..4))
        ACCESS  read-only
        STATUS  mandatory
        DESCRIPTION
            "Information about the error."
        ::= { cpqHeCriticalErrorEntry 5 }

    cpqHeCriticalErrorDesc OBJECT-TYPE
        SYNTAX  DisplayString (SIZE (0..255))
        ACCESS  read-only
        STATUS  mandatory
        DESCRIPTION
            "A text description of the critical error."
        ::= { cpqHeCriticalErrorEntry 6 }

-- ****************************************************************************
--   Health MIB Correctable Memory Error Group
--   =========================================
--
-- The compaq enterprise               (1.3.6.1.4.1.232)
--      cpqHealth Group                (1.3.6.1.4.1.232.6)
--       cpqHeComponent Group          (1.3.6.1.4.1.232.6.2)
--        cpqHeCorrectableMemory Group (1.3.6.1.4.1.232.6.2.3)
--
--  The cpqHeCorrectableMemory group describes the health correctable memory
--  error log.
--
--  Implementation of the cpqHeCorrectableMemory group is mandatory for all
--  agents that support the Compaq Health MIB on a system that has the
--  correctable memory feature.
--
-- ****************************************************************************

    cpqHeCorrMemLogStatus OBJECT-TYPE
        SYNTAX  INTEGER {
            other(1),
            notSupported(2),
            disabled(3),
            enabled(4)
            }
        ACCESS  read-only
        STATUS  mandatory
        DESCRIPTION
            "This value specifies whether this system is currently tracking
            correctable memory errors."
        ::= { cpqHeCorrectableMemory 1 }

    cpqHeCorrMemLogCondition OBJECT-TYPE
        SYNTAX  INTEGER {
            other(1),
            ok(2),
            degraded(3),
            failed(4)
            }
        ACCESS  read-only
        STATUS  mandatory
        DESCRIPTION
            "This value specifies the overall condition of the correctable
            memory error log feature."
        ::= { cpqHeCorrectableMemory 2 }

    cpqHeCorrMemTotalErrs OBJECT-TYPE
        SYNTAX  INTEGER (0..2147483647)
        ACCESS  read-only
        STATUS  deprecated
        DESCRIPTION
            "The number of correctable memory errors that have occurred."
        ::= { cpqHeCorrectableMemory 3 }

-- ****************************************************************************
--   Health MIB Correctable Memory Error Table
--   =========================================
--
-- The compaq enterprise               (1.3.6.1.4.1.232)
--      cpqHealth Group                (1.3.6.1.4.1.232.6)
--       cpqHeComponent Group          (1.3.6.1.4.1.232.6.2)
--        cpqHeCorrectableMemory Group (1.3.6.1.4.1.232.6.2.3)
--         cpqHeCorrMemErrTable        (1.3.6.1.4.1.232.6.2.3.4)
--
-- ****************************************************************************

    cpqHeCorrMemErrTable OBJECT-TYPE
        SYNTAX  SEQUENCE OF CpqHeCorrMemErrEntry
        ACCESS  not-accessible
        STATUS  mandatory
        DESCRIPTION
            "A table of correctable memory error descriptions."
        ::= { cpqHeCorrectableMemory 4 }

    cpqHeCorrMemErrEntry OBJECT-TYPE
        SYNTAX  CpqHeCorrMemErrEntry
        ACCESS  not-accessible
        STATUS  mandatory
        DESCRIPTION
            "A correctable memory error description."
        INDEX   { cpqHeCorrMemErrIndex }
        ::= { cpqHeCorrMemErrTable 1 }

    CpqHeCorrMemErrEntry ::= SEQUENCE {
        cpqHeCorrMemErrIndex       INTEGER,
        cpqHeCorrMemErrCount       INTEGER,
        cpqHeCorrMemErrTime        OCTET STRING,
        cpqHeCorrMemErrDdr         OCTET STRING,
        cpqHeCorrMemErrSyndrome    OCTET STRING,
        cpqHeCorrMemErrDesc        DisplayString,
        cpqHeCorrMemErrHwLocation  DisplayString
    }

    cpqHeCorrMemErrIndex OBJECT-TYPE
        SYNTAX  INTEGER (0..65535)
        ACCESS  read-only
        STATUS  mandatory
        DESCRIPTION
            "A number that uniquely specifies this correctable memory error
            description.  The entries will be in order of occurrence with the
            most recent new entry first."
        ::= { cpqHeCorrMemErrEntry 1 }

    cpqHeCorrMemErrCount OBJECT-TYPE
        SYNTAX  INTEGER (0..255)
        ACCESS  read-write
        STATUS  mandatory
        DESCRIPTION
            "The number of times this memory location has had a correctable
            memory error.  The value zero (0) indicates that the user has
            marked this error as corrected.  Marking errors as corrected may
            be performed with the Compaq Diagnostics or with a set operation
            of 0 on this variable.  Any non-zero valued set operation will
            fail."
        ::= { cpqHeCorrMemErrEntry 2 }

    cpqHeCorrMemErrTime OBJECT-TYPE
        SYNTAX  OCTET STRING (SIZE (0..3))
        ACCESS  read-only
        STATUS  mandatory
        DESCRIPTION
            "The time of the error: hour (first five bits), day of month
            (next 5 bits), month (next 4 bits), year of the current century
            (next 7 bits).  The last 3 bits are reserved."
        ::= { cpqHeCorrMemErrEntry 3 }

    cpqHeCorrMemErrDdr OBJECT-TYPE
        SYNTAX  OCTET STRING (SIZE (0..2))
        ACCESS  read-only
        STATUS  mandatory
        DESCRIPTION
            "The data destination register value.

            This contains information about the memory bank in which the
            error occurred.  The interpretation of this value is dependent
            on the machine type."
        ::= { cpqHeCorrMemErrEntry 4 }

    cpqHeCorrMemErrSyndrome OBJECT-TYPE
        SYNTAX  OCTET STRING (SIZE (0..2))
        ACCESS  read-only
        STATUS  mandatory
        DESCRIPTION
            "The memory syndrome value.

            This contains information about the memory module in which the
            error occurred.  The interpretation of this value is dependant
            on the machine type."
        ::= { cpqHeCorrMemErrEntry 5 }

    cpqHeCorrMemErrDesc OBJECT-TYPE
        SYNTAX  DisplayString (SIZE (0..255))
        ACCESS  read-only
        STATUS  mandatory
        DESCRIPTION
            "A text description of the correctable memory error."
        ::= { cpqHeCorrMemErrEntry 6 }

    cpqHeCorrMemErrHwLocation  OBJECT-TYPE
        SYNTAX  DisplayString (SIZE (0..255))
        ACCESS  read-only
        STATUS  optional
        DESCRIPTION
            "A text description of the hardware location, on complex
             multi SBB hardware only, for the correctable memory error.
             A NULL string indicates that the hardware location could not
             be determined or is irrelevant."
        ::= { cpqHeCorrMemErrEntry 7 }

    cpqHeCorrMemErrorCntThresh OBJECT-TYPE
        SYNTAX  INTEGER (0..2147483647)
        ACCESS  read-only
        STATUS  mandatory
        DESCRIPTION
            "The error threshold for Correctable memory errors. When
            cpqHeCorrMemErrCount is greater than or equal to this value
            user action is required to replace the failing memory module."
        ::= { cpqHeCorrectableMemory 5 }

-- ****************************************************************************
--   Health MIB Automatic Server Recovery (ASR) Group
--   ================================================
--
-- The compaq enterprise               (1.3.6.1.4.1.232)
--      cpqHealth Group                (1.3.6.1.4.1.232.6)
--       cpqHeComponent Group          (1.3.6.1.4.1.232.6.2)
--        cpqHeAsr Group               (1.3.6.1.4.1.232.6.2.5)
--
--  The cpqHeAsr group describes the Automatic Server Recovery Health
--  feature.
--
--  Implementation of the cpqHeAsr group is mandatory for all agents that
--  support the Compaq Health MIB on a system that supports the ASR feature.
--
-- ****************************************************************************

    cpqHeAsrStatus OBJECT-TYPE
        SYNTAX  INTEGER {
            other(1),
            notAvailable(2),
            disabled(3),
            enabled(4)
            }
        ACCESS  read-write
        STATUS  mandatory
        DESCRIPTION
            "The Automatic Server Recovery feature status.

            If this object is currently other(1) or notAvailable(2) all
            set operations will fail.  Any attempt to set this object to
            other(1) or notAvailable(2) by a management station will fail.

            Setting this object to disabled(3) or enabled(4) will disable
            or enable the ASR feature.

            Setting this object to disabled(3) will disable the following
            objects:
                cpqHeAsrPagerStatus
                cpqHeAsrDialInStatus
                cpqHeAsrDialOutStatus"
        ::= { cpqHeAsr 1 }

    cpqHeAsrMajorVersion OBJECT-TYPE
        SYNTAX  INTEGER (0..255)
        ACCESS  read-only
        STATUS  mandatory
        DESCRIPTION
            "The major version number of the Automatic Server Recovery
            feature hardware."
        ::= { cpqHeAsr 2 }

    cpqHeAsrMinorVersion OBJECT-TYPE
        SYNTAX  INTEGER (0..255)
        ACCESS  read-only
        STATUS  mandatory
        DESCRIPTION
            "The minor version number of the Automatic Server Recovery
            feature hardware."
        ::= { cpqHeAsr 3 }

    cpqHeAsrTimeout OBJECT-TYPE
        SYNTAX  INTEGER
        ACCESS  read-write
        STATUS  mandatory
        DESCRIPTION
            "The time-out in minutes for the Automatic Server Recovery
            feature hardware.  If the variable is not supported, a value
            of -1 will be returned."
        ::= { cpqHeAsr 4 }

    cpqHeAsrBaseIo OBJECT-TYPE
        SYNTAX  INTEGER
        ACCESS  read-only
        STATUS  mandatory
        DESCRIPTION
            "The Automatic Server Recovery feature Base I/O address."
        ::= { cpqHeAsr 5 }

    cpqHeAsrPost OBJECT-TYPE
        SYNTAX  INTEGER {
            other(1),
            failed(2),
            ok(3)
            }
        ACCESS  read-only
        STATUS  deprecated
        DESCRIPTION
            "Indicates if the Automatic Server Recovery timer passed
             the server power-on self test."
        ::= { cpqHeAsr 6 }

    cpqHeAsrReset OBJECT-TYPE
        SYNTAX  INTEGER {
            other(1),
            manualReset(2),
            asrReset(3),
            viewed-asrReset(4)
            }
        ACCESS  read-write
        STATUS  mandatory
        DESCRIPTION
            "Indicates if the previous reset was caused by the ASR
             timer. An asrReset(3) condition may be changed with a
             viewed-asrReset(4) set operation.  This is only valid
             if this variable's current value is asrReset(3).  Setting
             this variable to any other value than viewed-asrReset(4)
             will fail."
        ::= { cpqHeAsr 7 }

    cpqHeAsrReboot OBJECT-TYPE
        SYNTAX  INTEGER {
            other(1),
            bootOs(2),
            bootUtilities(3)
            }
        ACCESS  read-write
        STATUS  mandatory
        DESCRIPTION
            "Indicates what software should be started when the server is
             rebooted by the ASR feature.

             If this object is currently set to other(1), set operations
             will fail.  This object may not be set to other(1) by a
             management station.

             Setting this object to bootOs(2) or bootUtilities(3)
             will select the software to be started after an ASR reboot."
        ::= { cpqHeAsr 8 }

    cpqHeAsrRebootLimit OBJECT-TYPE
        SYNTAX  INTEGER
        ACCESS  read-only
        STATUS  mandatory
        DESCRIPTION
            "The number of ASR timer reboots that should cause the server to
            boot the firmware console and override the standard reboot
            setting (cpqHeAsrReboot).  If this value is 0 then no limit is
            defined and the standard reboot option will always be used.  If
            the variable is not supported, a value of -1 will be returned."
        ::= { cpqHeAsr 9 }

    cpqHeAsrRebootCount OBJECT-TYPE
        SYNTAX  INTEGER
        ACCESS  read-write
        STATUS  mandatory
        DESCRIPTION
            "The number of ASR reboots that have occurred on this server
             since the last manual reboot. Reboot count may be reset with
             a zero valued set operation on this variable. Setting this
             value to a non-zero value will fail.  If the variable is not
             supported, a value of -1 will be returned."
        ::= { cpqHeAsr 10 }

    cpqHeAsrPagerStatus OBJECT-TYPE
        SYNTAX  INTEGER {
            other(1),
            disabled(2),
            enabled(3)
            }
        ACCESS  read-write
        STATUS  mandatory
        DESCRIPTION
            "The status of the ASR pager feature.

            If the current value of this object is not other(1), it may
            be set to disabled(2) or enabled(3).  Attempting a set operation
            while the value is other(1) will fail.  Attempting to set the
            value to other(1) will fail.

            Setting this object to enabled(3) will enable the
            cpqHeAsrStatus object."
        ::= { cpqHeAsr 11 }

    cpqHeAsrPagerNumber OBJECT-TYPE
        SYNTAX  DisplayString (SIZE (0..60))
        ACCESS  read-write
        STATUS  mandatory
        DESCRIPTION
            "The pager number to be dialed after an ASR reboot."
        ::= { cpqHeAsr 12 }

    cpqHeAsrCommPort OBJECT-TYPE
        SYNTAX  INTEGER
        ACCESS  read-write
        STATUS  mandatory
        DESCRIPTION
            "The communication port to be used by the firmware pager and
            console.  The value zero (0) indicates this setting is undefined.

            If the current value of this object is zero (0) any
            attempt to set this object from a management station
            will fail.  Any attempt to set this object to zero (0)
            by a management station will fail.  If the variable is not
            supported, a value of -1 will be returned."
        ::= { cpqHeAsr 13 }

    cpqHeAsrBaudRate OBJECT-TYPE
        SYNTAX  INTEGER
        ACCESS  read-only
        STATUS  mandatory
        DESCRIPTION
            "The baud rate to be used by the firmware pager and console.
            The value zero (0) indicates this setting is undefined.  If the
            variable is not supported, a value of -1 will be returned."
        ::= { cpqHeAsr 14 }

    cpqHeAsrPagerMessage OBJECT-TYPE
        SYNTAX  DisplayString (SIZE (0..8))
        ACCESS  read-write
        STATUS  mandatory
        DESCRIPTION
            "The 8 character pager message entered by the user."
        ::= { cpqHeAsr 15 }

    cpqHeAsrBootFail OBJECT-TYPE
        SYNTAX  INTEGER {
            other(1),
            interrupt18(2)
            }
        ACCESS  read-only
        STATUS  deprecated
        DESCRIPTION
            "The action to be taken if an ASR reboot failure occurs."
        ::= { cpqHeAsr 16 }

    cpqHeAsrCondition OBJECT-TYPE
        SYNTAX  INTEGER {
            other(1),
            ok(2),
            degraded(3),
            failed(4)
            }
        ACCESS  read-only
        STATUS  mandatory
        DESCRIPTION
            "This value specifies the overall condition of the ASR feature."
        ::= { cpqHeAsr 17 }

    cpqHeAsrDialInStatus OBJECT-TYPE
        SYNTAX  INTEGER {
            other(1),
            disabled(2),
            enabled(3)
            }
        ACCESS  read-write
        STATUS  mandatory
        DESCRIPTION
            "The status of the ASR dial in feature.

            If the current value of this object is other(1) any attempt to
            set this object from a management station will fail.  Any
            attempt to set this object to other(1) by a management station
            will fail.

            Setting this object to enabled(3) will enable the
            cpqHeAsrStatus object."
        ::= { cpqHeAsr 18 }

    cpqHeAsrDialOutStatus OBJECT-TYPE
        SYNTAX  INTEGER {
            other(1),
            disabled(2),
            enabled(3)
            }
        ACCESS  read-write
        STATUS  mandatory
        DESCRIPTION
            "The status of the ASR dial out feature.

            If the current value of this object is other(1) any attempt to
            set this object from a management station will fail.  Any
            attempt to set this object to other(1) by a management station
            will fail.

            Setting this object to enabled(3) will enable the
            cpqHeAsrStatus and the cpqHeAsrDialInStatus objects."
        ::= { cpqHeAsr 19 }

    cpqHeAsrDialOutNumber OBJECT-TYPE
        SYNTAX  DisplayString (SIZE (0..60))
        ACCESS  read-write
        STATUS  mandatory
        DESCRIPTION
            "The phone number to be dialed for remote diagnostics if an ASR
            reset occurs."
        ::= { cpqHeAsr 20 }

    cpqHeAsrNetworkAccessStatus OBJECT-TYPE
        SYNTAX  INTEGER {
            other(1),
            disabled(2),
            enabled(3)
            }
        ACCESS  read-write
        STATUS  mandatory
        DESCRIPTION
            "The status of the ASR network access feature.

            If the current value of this object is other(1) any attempt to
            set this object from a management station will fail.  Any
            attempt to set this object to other(1) by a management station
            will fail."
        ::= { cpqHeAsr 21 }

-- ****************************************************************************
--   Health MIB Thermal Group
--   ========================
--
-- The compaq enterprise               (1.3.6.1.4.1.232)
--      cpqHealth Group                (1.3.6.1.4.1.232.6)
--       cpqHeComponent Group          (1.3.6.1.4.1.232.6.2)
--        cpqHeThermal Group           (1.3.6.1.4.1.232.6.2.6)
--
--  The cpqHeThermal group describes the status of the temperature and the
--  fans that regulate the temperature.
--
--  Implementation of the cpqHeThermal group is mandatory for all agents
--  that support the Compaq Health MIB on a system that supports the thermal
--  sensing features.
--
-- ****************************************************************************

    cpqHeThermalCondition OBJECT-TYPE
        SYNTAX  INTEGER {
            other(1),
            ok(2),
            degraded(3),
            failed(4)
            }
        ACCESS  read-only
        STATUS  mandatory
        DESCRIPTION
            "This value specifies the overall condition of the system's
            thermal environment."
        ::= { cpqHeThermal 1 }

    cpqHeThermalDegradedAction OBJECT-TYPE
        SYNTAX  INTEGER {
            other(1),
            continue(2),
            shutdown(3)
            }
        ACCESS  read-write
        STATUS  mandatory
        DESCRIPTION
            "The action to perform when the thermal condition is degraded.

            This value will be one of the following:
            other(1)
              This feature is not supported by this system or driver.

            continue(2)
              The system should be allowed to continue.

            shutdown(3)
              The system should be shutdown."
        ::= { cpqHeThermal 2 }

    cpqHeThermalTempStatus OBJECT-TYPE
        SYNTAX  INTEGER {
            other(1),
            ok(2),
            degraded(3),
            failed(4)
            }
        ACCESS  read-only
        STATUS  mandatory
        DESCRIPTION
            "The status of the system's temperature sensors:

            This value will be one of the following:
            other(1)
              Temp sensing is not supported by this system or driver.

            ok(2)
              All temp sensors are within normal operating range.

            degraded(3)
              A temp sensor is outside of normal operating range.

            failed(4)
              A temp sensor detects a condition that could permanently
              damage the system.

            The system will automatically shutdown if the failed(4) condition
            results, so it is unlikely that this value will ever be returned
            by the agent.  If the cpqHeThermalDegradedAction is set to
            shutdown(3) the system will be shutdown if the degraded(3)
            condition occurs."
        ::= { cpqHeThermal 3 }

    cpqHeThermalSystemFanStatus OBJECT-TYPE
        SYNTAX  INTEGER {
            other(1),
            ok(2),
            degraded(3),
            failed(4)
            }
        ACCESS  read-only
        STATUS  mandatory
        DESCRIPTION
            "The status of the fan(s) in the system.

            This value will be one of the following:
            other(1)
              Fan status detection is not supported by this system or driver.

            ok(2)
              All fans are operating properly.

            degraded(3)
              A non-required fan is not operating properly.

            failed(4)
              A required fan is not operating properly.

            If the cpqHeThermalDegradedAction is set to shutdown(3) the
            system will be shutdown if the failed(4) condition occurs."
        ::= { cpqHeThermal 4 }

    cpqHeThermalCpuFanStatus OBJECT-TYPE
        SYNTAX  INTEGER {
            other(1),
            ok(2),
            failed(4)
            }
        ACCESS  read-only
        STATUS  mandatory
        DESCRIPTION
            "The status of the processor fan(s) in the system.

            This value will be one of the following:
            other(1)
              Fan status detection is not supported by this system or driver.

            ok(2)
              All fans are operating properly.

            failed(4)
              A fan is not operating properly.

            The system will be shutdown if the failed(4) condition occurs."
        ::= { cpqHeThermal 5 }

-- ****************************************************************************
--   Health MIB Thermal Fan Table
--   ============================
--
-- The compaq enterprise               (1.3.6.1.4.1.232)
--      cpqHealth Group                (1.3.6.1.4.1.232.6)
--       cpqHeComponent Group          (1.3.6.1.4.1.232.6.2)
--        cpqHeThermal Group           (1.3.6.1.4.1.232.6.2.6)
--         cpqHeThermalFanTable        (1.3.6.1.4.1.232.6.2.6.6)
--
-- ****************************************************************************

    cpqHeThermalFanTable OBJECT-TYPE
        SYNTAX  SEQUENCE OF CpqHeThermalFanEntry
        ACCESS  not-accessible
        STATUS  mandatory
        DESCRIPTION
            "A table of fan descriptions."
        ::= { cpqHeThermal 6 }

    cpqHeThermalFanEntry OBJECT-TYPE
        SYNTAX  CpqHeThermalFanEntry
        ACCESS  not-accessible
        STATUS  mandatory
        DESCRIPTION
            "A fan description."
        INDEX   { cpqHeThermalFanIndex }
        ::= { cpqHeThermalFanTable 1 }

    CpqHeThermalFanEntry ::= SEQUENCE {
        cpqHeThermalFanIndex       INTEGER,
        cpqHeThermalFanRequired    INTEGER,
        cpqHeThermalFanPresent     INTEGER,
        cpqHeThermalFanCpuFan      INTEGER,
        cpqHeThermalFanStatus      INTEGER,
        cpqHeThermalFanHwLocation  DisplayString
    }

    cpqHeThermalFanIndex OBJECT-TYPE
        SYNTAX  INTEGER (0..8)
        ACCESS  read-only
        STATUS  mandatory
        DESCRIPTION
            "A number that uniquely specifies this fan description."
        ::= { cpqHeThermalFanEntry 1 }

    cpqHeThermalFanRequired OBJECT-TYPE
        SYNTAX  INTEGER {
            other(1),
            nonRequired(2),
            required(3)
            }
        ACCESS  read-only
        STATUS  mandatory
        DESCRIPTION
            "This specifies if the fan described is required for proper
            operation of the system."
        ::= { cpqHeThermalFanEntry 2 }

    cpqHeThermalFanPresent OBJECT-TYPE
        SYNTAX  INTEGER {
            other(1),
            absent(2),
            present(3)
            }
        ACCESS  read-only
        STATUS  mandatory
        DESCRIPTION
            "This specifies if the fan described is present in the system."
        ::= { cpqHeThermalFanEntry 3 }

    cpqHeThermalFanCpuFan OBJECT-TYPE
        SYNTAX  INTEGER {
            other(1),
            systemFan(2),
            cpuFan(3)
            }
        ACCESS  read-only
        STATUS  mandatory
        DESCRIPTION
            "This specifies if the described fan is intended specifically
             to cool the CPU(s)."
        ::= { cpqHeThermalFanEntry 4 }

    cpqHeThermalFanStatus OBJECT-TYPE
        SYNTAX  INTEGER {
            other(1),
            ok(2),
            failed(4)
            }
        ACCESS  read-only
        STATUS  mandatory
        DESCRIPTION
            "This specifies if the fan described is operating properly.

            This value will be one of the following:
            other(1)
              Fan status detection is not supported by this system or driver.

            ok(2)
              The fan is operating properly.

            failed(4)
              The fan is not operating properly."
        ::= { cpqHeThermalFanEntry 5 }

    cpqHeThermalFanHwLocation  OBJECT-TYPE
        SYNTAX  DisplayString (SIZE (0..255))
        ACCESS  read-only
        STATUS  optional
        DESCRIPTION
            "A text description of the hardware location, on complex
             multi SBB hardware only, for the fan.
             A NULL string indicates that the hardware location could not
             be determined or is irrelevant."
        ::= { cpqHeThermalFanEntry 6 }


-- ****************************************************************************
--   Health MIB Fault Tolerant Fan Table
--   ===================================
--
-- The compaq enterprise               (1.3.6.1.4.1.232)
--      cpqHealth Group                (1.3.6.1.4.1.232.6)
--       cpqHeComponent Group          (1.3.6.1.4.1.232.6.2)
--        cpqHeThermal Group           (1.3.6.1.4.1.232.6.2.6)
--         cpqHeFltTolFanTable         (1.3.6.1.4.1.232.6.2.6.7)
--
-- ****************************************************************************

    cpqHeFltTolFanTable OBJECT-TYPE
        SYNTAX  SEQUENCE OF CpqHeFltTolFanEntry
        ACCESS  not-accessible
        STATUS  mandatory
        DESCRIPTION
            "A table of Fault Tolerant Fan Entries."
        ::= { cpqHeThermal 7 }

    cpqHeFltTolFanEntry OBJECT-TYPE
        SYNTAX  CpqHeFltTolFanEntry
        ACCESS  not-accessible
        STATUS  mandatory
        DESCRIPTION
            "A Fault Tolerant Fan Entry."
        INDEX   { cpqHeFltTolFanChassis, cpqHeFltTolFanIndex }
        ::= { cpqHeFltTolFanTable 1 }

    CpqHeFltTolFanEntry ::= SEQUENCE {
        cpqHeFltTolFanChassis                   INTEGER,
        cpqHeFltTolFanIndex                     INTEGER,
        cpqHeFltTolFanLocale                    INTEGER,
        cpqHeFltTolFanPresent                   INTEGER,
        cpqHeFltTolFanType                      INTEGER,
        cpqHeFltTolFanSpeed                     INTEGER,
        cpqHeFltTolFanRedundant                 INTEGER,
        cpqHeFltTolFanRedundantPartner          INTEGER,
        cpqHeFltTolFanCondition                 INTEGER,
        cpqHeFltTolFanHotPlug                   INTEGER,
        cpqHeFltTolFanHwLocation                DisplayString
    }

    cpqHeFltTolFanChassis OBJECT-TYPE
        SYNTAX  INTEGER
        ACCESS  read-only
        STATUS  mandatory
        DESCRIPTION
            "The System Chassis number."
        ::= { cpqHeFltTolFanEntry 1 }

    cpqHeFltTolFanIndex OBJECT-TYPE
        SYNTAX  INTEGER
        ACCESS  read-only
        STATUS  mandatory
        DESCRIPTION
            "A number that uniquely specifies this fan description."
        ::= { cpqHeFltTolFanEntry 2 }

    cpqHeFltTolFanLocale OBJECT-TYPE
        SYNTAX  INTEGER {
            other(1),
            unknown(2),
            system(3),
            systemBoard(4),
            ioBoard(5),
            cpu(6),
            memory(7),
            storage(8),
            removableMedia(9),
            powerSupply(10),
            ambient(11),
            chassis(12),
            bridgeCard(13)
            }
        ACCESS  read-only
        STATUS  mandatory
        DESCRIPTION
            "This specifies the location of the fan in the system."
        ::= { cpqHeFltTolFanEntry 3 }

    cpqHeFltTolFanPresent OBJECT-TYPE
        SYNTAX  INTEGER {
            other(1),
            absent(2),
            present(3)
            }
        ACCESS  read-only
        STATUS  mandatory
        DESCRIPTION
            "This specifies if the fan described is present in the system."
        ::= { cpqHeFltTolFanEntry 4 }

    cpqHeFltTolFanType OBJECT-TYPE
        SYNTAX  INTEGER {
            other(1),
            tachOutput(2),
            spinDetect(3)
            }
        ACCESS  read-only
        STATUS  mandatory
        DESCRIPTION
            "This specifies the type of fan.

            other(1)
              The type of fan could not be determined.

            tachOutput(2)
              The fan can increase speed for greater cooling.  Implies
              spin detect.

            spinDetect(3)
              The fan can detect when the fan stops spinning."
        ::= { cpqHeFltTolFanEntry 5 }

    cpqHeFltTolFanSpeed OBJECT-TYPE
        SYNTAX  INTEGER {
            other(1),
            normal(2),
            high(3)
            }
        ACCESS  read-only
        STATUS  mandatory
        DESCRIPTION
            "This specifies the speed of the fan.  This value will be set
            if the fan type is tachOutput."
        ::= { cpqHeFltTolFanEntry 6 }

    cpqHeFltTolFanRedundant OBJECT-TYPE
        SYNTAX  INTEGER {
            other(1),
            notRedundant(2),
            redundant(3)
            }
        ACCESS  read-only
        STATUS  mandatory
        DESCRIPTION
            "This specifies if the fan is in a redundant configuration."
        ::= { cpqHeFltTolFanEntry 7 }

    cpqHeFltTolFanRedundantPartner OBJECT-TYPE
        SYNTAX  INTEGER
        ACCESS  read-only
        STATUS  mandatory
        DESCRIPTION
            "This specifies the index of the redundant partner.  A value
            of zero will be used if there is no redundant partner."
        ::= { cpqHeFltTolFanEntry 8 }

    cpqHeFltTolFanCondition OBJECT-TYPE
        SYNTAX  INTEGER {
            other(1),
            ok(2),
            degraded(3),
            failed(4)
            }
        ACCESS  read-only
        STATUS  mandatory
        DESCRIPTION
            "The condition of the fan.

            This value will be one of the following:
            other(1)
              Fan status detection is not supported by this system or driver.

            ok(2)
              The fan is operating properly.

            degraded(2)
              A redundant fan is not operating properly.

            failed(4)
              A non-redundant fan is not operating properly."
        ::= { cpqHeFltTolFanEntry 9 }

    cpqHeFltTolFanHotPlug OBJECT-TYPE
        SYNTAX  INTEGER {
            other(1),
            nonHotPluggable(2),
            hotPluggable(3)
            }
        ACCESS  read-only
        STATUS  mandatory
        DESCRIPTION
            "This indicates if the fan is capable of being removed and/or
            inserted while the system is in an operational state.

            If the value is hotPluggable(3), the fan can be safely
            removed if and only if the cpqHeFltTolFanRedundant
            field is in a redundant(3) state.

            This value will be one of the following:
            other(1)
              The state could not be determined.

            nonHotPluggable(2)
              The fan is not hot plug capable.

            hotPluggable(3)
              The fan is hot plug capable and can be removed if
              the system is operating in a redundant state.  A fan
              may be added to an empty fan bay."
        ::= { cpqHeFltTolFanEntry 10 }

    cpqHeFltTolFanHwLocation OBJECT-TYPE
        SYNTAX  DisplayString (SIZE (0..255))
        ACCESS  read-only
        STATUS  optional
        DESCRIPTION
            "A text description of the hardware location, on complex
             multi SBB hardware only, for the fan.
             A NULL string indicates that the hardware location could not
             be determined or is irrelevant."
        ::= { cpqHeFltTolFanEntry 11 }


-- ****************************************************************************
--   Health MIB Temperature Sensor Table
--   ===================================
--
-- The compaq enterprise               (1.3.6.1.4.1.232)
--      cpqHealth Group                (1.3.6.1.4.1.232.6)
--       cpqHeComponent Group          (1.3.6.1.4.1.232.6.2)
--        cpqHeThermal Group           (1.3.6.1.4.1.232.6.2.6)
--         cpqHeTemperatureTable       (1.3.6.1.4.1.232.6.2.6.8)
--
-- ****************************************************************************

    cpqHeTemperatureTable OBJECT-TYPE
        SYNTAX  SEQUENCE OF CpqHeTemperatureEntry
        ACCESS  not-accessible
        STATUS  mandatory
        DESCRIPTION
            "A table of Temperature Sensor Entries."
        ::= { cpqHeThermal 8 }

    cpqHeTemperatureEntry OBJECT-TYPE
        SYNTAX  CpqHeTemperatureEntry
        ACCESS  not-accessible
        STATUS  mandatory
        DESCRIPTION
            "A Temperature Sensor Entry."
        INDEX   { cpqHeTemperatureChassis, cpqHeTemperatureIndex }
        ::= { cpqHeTemperatureTable 1 }

    CpqHeTemperatureEntry ::= SEQUENCE {
        cpqHeTemperatureChassis                   INTEGER,
        cpqHeTemperatureIndex                     INTEGER,
        cpqHeTemperatureLocale                    INTEGER,
        cpqHeTemperatureCelsius                   INTEGER,
        cpqHeTemperatureThreshold                 INTEGER,
        cpqHeTemperatureCondition                 INTEGER,
        cpqHeTemperatureThresholdType             INTEGER,
        cpqHeTemperatureHwLocation                DisplayString
    }

    cpqHeTemperatureChassis OBJECT-TYPE
        SYNTAX  INTEGER
        ACCESS  read-only
        STATUS  mandatory
        DESCRIPTION
            "The System Chassis number."
        ::= { cpqHeTemperatureEntry 1 }

    cpqHeTemperatureIndex OBJECT-TYPE
        SYNTAX  INTEGER
        ACCESS  read-only
        STATUS  mandatory
        DESCRIPTION
            "A number that uniquely specifies this temperature sensor
            description."
        ::= { cpqHeTemperatureEntry 2 }

    cpqHeTemperatureLocale OBJECT-TYPE
        SYNTAX  INTEGER {
            other(1),
            unknown(2),
            system(3),
            systemBoard(4),
            ioBoard(5),
            cpu(6),
            memory(7),
            storage(8),
            removableMedia(9),
            powerSupply(10),
            ambient(11),
            chassis(12),
            bridgeCard(13)
            }
        ACCESS  read-only
        STATUS  mandatory
        DESCRIPTION
            "This specifies the location of the temperature sensor
            present in the system."
        ::= { cpqHeTemperatureEntry 3 }

    cpqHeTemperatureCelsius OBJECT-TYPE
        SYNTAX  INTEGER
        ACCESS  read-only
        STATUS  mandatory
        DESCRIPTION
            "This is the current temperature sensor reading in degrees
            celsius.

            If this value cannot be determined by software, then a value
            of -1 will be returned."
        ::= { cpqHeTemperatureEntry 4 }

    cpqHeTemperatureThreshold OBJECT-TYPE
        SYNTAX  INTEGER
        ACCESS  read-write
        STATUS  mandatory
        DESCRIPTION
            "This is the shutdown threshold temperature sensor setting
            in degrees celsius.  This is the temerature in which the
            sensor will be considered to be in a failed state thus
            causing the system to be shutdown.

            If this value cannot be determined by software, then a value
            of -1 will be returned.

            Only the Ambient zone type allows setting of the threshold
            temperature."
        ::= { cpqHeTemperatureEntry 5 }

    cpqHeTemperatureCondition OBJECT-TYPE
        SYNTAX  INTEGER {
            other(1),
            ok(2),
            degraded(3),
            failed(4)
            }
        ACCESS  read-only
        STATUS  mandatory
        DESCRIPTION
            "The Temperature sensor condition.

            This value will be one of the following:
            other(1)
              Temperature could not be determined.

            ok(2)
              The temperature sensor is within normal operating range.

            degraded(3)
              The temperature sensor is outside of normal operating range.

            failed(4)
              The temperature sensor detects a condition that could
              permanently damage the system.

            The system will automatically shutdown if the failed(4) condition
            results, so it is unlikely that this value will ever be returned
            by the agent.  If the cpqHeThermalDegradedAction is set to
            shutdown(3) the system will be shutdown if the degraded(3)
            condition occurs."
        ::= { cpqHeTemperatureEntry 6 }

    cpqHeTemperatureThresholdType OBJECT-TYPE
        SYNTAX  INTEGER {
            other(1),
            blowout(5),
            caution(9),
            critical(15)
            }
        ACCESS  read-only
        STATUS  mandatory
        DESCRIPTION
            "This specifies the type of this instance of temperature
            sensor.

            This value will be one of the following:
            other(1)
              Temperature threshold type could not be determined.

            blowout(5)
              If a blowout(5) temperature sensor reaches its threshold,
              the fan or fans in the area of the temperature sensor will
              increase in speed in an attempt to reduce the temperature
              before a caution or critical threshold is reached.

            caution(9)
              If a caution(9) temperature sensor reaches its threshold,
              the cpqHeTemperatureCondition will be set to degraded(3)
              and the system will either continue or shutdown depending
              on the setting of cpqHeThermalDegradedAction.

            critical(15)
              If a critical(15) temperature sensor reaches its threshold,
              the cpqHeTemperatureCondition will be set to failed(4)
              and the system will shutdown."
        ::= { cpqHeTemperatureEntry 7 }

    cpqHeTemperatureHwLocation OBJECT-TYPE
        SYNTAX  DisplayString (SIZE (0..255))
        ACCESS  read-only
        STATUS  optional
        DESCRIPTION
            "A text description of the hardware location, on complex
             multi SBB hardware only, for the temperature sensor.
             A NULL string indicates that the hardware location could not
             be determined or is irrelevant."
        ::= { cpqHeTemperatureEntry 8 }

-- ****************************************************************************
--   Health MIB Post Message Group
--   =============================
--
-- The compaq enterprise               (1.3.6.1.4.1.232)
--      cpqHealth Group                (1.3.6.1.4.1.232.6)
--       cpqHeComponent Group          (1.3.6.1.4.1.232.6.2)
--        cpqHePostMsg Group           (1.3.6.1.4.1.232.6.2.7)
--
--  The cpqHePostMsg group contains a table of the non-critical POST
--  errors that occurred during the last reboot.
--
--  Implementation of the cpqHePostMsg group is mandatory for all agents
--  that support the Compaq Health MIB on a system that supports the POST
--  error recording feature.
--
-- ****************************************************************************

    cpqHePostMsgCondition OBJECT-TYPE
        SYNTAX  INTEGER {
            other(1),
            ok(2),
            degraded(3),
            failed(4)
            }
        ACCESS  read-only
        STATUS  mandatory
        DESCRIPTION
            "This value specifies the overall condition of the POST
            error recording feature."
        ::= { cpqHePostMsg 1 }

-- ****************************************************************************
--   Health MIB Post Message Table
--   =============================
--
-- The compaq enterprise               (1.3.6.1.4.1.232)
--      cpqHealth Group                (1.3.6.1.4.1.232.6)
--       cpqHeComponent Group          (1.3.6.1.4.1.232.6.2)
--        cpqHePostMsg Group           (1.3.6.1.4.1.232.6.2.7)
--         cpqHePostMsgTable           (1.3.6.1.4.1.232.6.2.7.2)
--
--      This table may be empty if no errors occurred during POST.
--
-- ****************************************************************************

    cpqHePostMsgTable OBJECT-TYPE
        SYNTAX  SEQUENCE OF CpqHePostMsgEntry
        ACCESS  not-accessible
        STATUS  mandatory
        DESCRIPTION
            "A table of POST error message numbers."
        ::= { cpqHePostMsg 2 }

    cpqHePostMsgEntry OBJECT-TYPE
        SYNTAX  CpqHePostMsgEntry
        ACCESS  not-accessible
        STATUS  mandatory
        DESCRIPTION
            "A POST error message number."
        INDEX   { cpqHePostMsgIndex }
        ::= { cpqHePostMsgTable 1 }

    CpqHePostMsgEntry ::= SEQUENCE {
        cpqHePostMsgIndex       INTEGER,
        cpqHePostMsgCode        INTEGER,
        cpqHePostMsgDesc        DisplayString
    }


    cpqHePostMsgIndex OBJECT-TYPE
        SYNTAX  INTEGER (0..255)
        ACCESS  read-only
        STATUS  mandatory
        DESCRIPTION
            "A number that uniquely specifies this POST error description."
        ::= { cpqHePostMsgEntry 1 }

    cpqHePostMsgCode OBJECT-TYPE
        SYNTAX  INTEGER (0..255)
        ACCESS  read-only
        STATUS  mandatory
        DESCRIPTION
            "This specifies POST message number for this error."
        ::= { cpqHePostMsgEntry 2 }

    cpqHePostMsgDesc OBJECT-TYPE
         SYNTAX  DisplayString (SIZE (0..255))
         ACCESS  read-only
         STATUS  mandatory
         DESCRIPTION
             "This contains a text description of the POST error.
              A string of length zero (0) will be returned if no description
              is available."
         ::= { cpqHePostMsgEntry 3 }

    cpqHePostMsgEv OBJECT-TYPE
        SYNTAX  OCTET STRING (SIZE (0..8))
        ACCESS  read-write
        STATUS  mandatory
        DESCRIPTION
            "The EV used to store 8 non-critical POST error codes
             for use with Quicktest, Utilities, and CIM. Setting
             this variable with a zero length octet string will
             clear this variable.  All other set operations will
             fail."
        ::= { cpqHePostMsg 3 }


-- ****************************************************************************
--   Health MIB System Utilization Group
--   ===================================
--
-- The compaq enterprise               (1.3.6.1.4.1.232)
--      cpqHealth Group                (1.3.6.1.4.1.232.6)
--       cpqHeComponent Group          (1.3.6.1.4.1.232.6.2)
--        cpqHeSysUtil Group           (1.3.6.1.4.1.232.6.2.8)
--
--  The cpqHeSysUtil group contains measures of system utilization.
--  This group includes long term utilization information like the total
--  server up time since originally configured.  This group also contains
--  current operating utilization information such as the current EISA bus
--  utilization.
--
--  Implementation of the cpqHeSysUtil group is mandatory for all agents
--  that support the Compaq Health MIB on a system that supports any system
--  utilization features.
--
-- ****************************************************************************

    cpqHeSysUtilLifeTime OBJECT-TYPE
        SYNTAX  INTEGER (0..2147483647)
        ACCESS  read-only
        STATUS  mandatory
        DESCRIPTION
            "The total time (in minutes) the system has been in full
             operation (while the server health supporting software was
             running)."
        ::= { cpqHeSysUtil 1 }

    cpqHeSysUtilEisaBusMin OBJECT-TYPE
        SYNTAX  INTEGER
        ACCESS  read-only
        STATUS  mandatory
        DESCRIPTION
            "The EISA bus utilization as a percentage of the theoretical
            maximum during the last minute.  A value of -1 indicates that
            this feature is not supported on this machine or is not
            available."
        ::= { cpqHeSysUtil 2 }

    cpqHeSysUtilEisaBusFiveMin OBJECT-TYPE
        SYNTAX  INTEGER
        ACCESS  read-only
        STATUS  mandatory
        DESCRIPTION
            "The EISA bus utilization as a percentage of the theoretical
            maximum during the last five minutes.  A value of -1 indicates
            that this feature is not supported on this machine or is not
            available."
        ::= { cpqHeSysUtil 3 }

    cpqHeSysUtilEisaBusThirtyMin OBJECT-TYPE
        SYNTAX  INTEGER
        ACCESS  read-only
        STATUS  mandatory
        DESCRIPTION
            "The EISA bus utilization as a percentage of the theoretical
            maximum during the last thirty minutes.  A value of -1
            indicates that this feature is not supported on this machine
            or is not available."
        ::= { cpqHeSysUtil 4 }

    cpqHeSysUtilEisaBusHour OBJECT-TYPE
        SYNTAX  INTEGER
        ACCESS  read-only
        STATUS  mandatory
        DESCRIPTION
            "The EISA bus utilization as a percentage of the theoretical
            maximum during the last hour.  A value of -1 indicates that
            this feature is not supported on this machine or is not
            available."
        ::= { cpqHeSysUtil 5 }

-- ****************************************************************************
--   Health MIB PCI Utilization Table
--   ====================================
--
-- The compaq enterprise               (1.3.6.1.4.1.232)
--      cpqHealth Group                (1.3.6.1.4.1.232.6)
--       cpqHeComponent Group          (1.3.6.1.4.1.232.6.2)
--        cpqHeSysUtil Group           (1.3.6.1.4.1.232.6.2.8)
--         cpqHeSysUtilPciTable        (1.3.6.1.4.1.232.6.2.8.6)
--
--
-- ****************************************************************************

    cpqHeSysUtilPciTable OBJECT-TYPE
        SYNTAX  SEQUENCE OF CpqHeSysUtilPciEntry
        ACCESS  not-accessible
        STATUS  mandatory
        DESCRIPTION
            "A table of PCI utilization numbers for a whole aggregate
            PCI bus or a specific device on that bus."
        ::= { cpqHeSysUtil 6 }

    cpqHeSysUtilPciEntry OBJECT-TYPE
        SYNTAX  CpqHeSysUtilPciEntry
        ACCESS  not-accessible
        STATUS  mandatory
        DESCRIPTION
            "PCI utilization entry"
        INDEX   { cpqHeSysUtilPciIndex }
        ::= { cpqHeSysUtilPciTable 1 }

    CpqHeSysUtilPciEntry ::= SEQUENCE {
        cpqHeSysUtilPciIndex     INTEGER,
        cpqHeSysUtilPciBus       INTEGER,
        cpqHeSysUtilPciDevice    INTEGER,
        cpqHeSysUtilPciMin       INTEGER,
        cpqHeSysUtilPciFiveMin   INTEGER,
        cpqHeSysUtilPciThirtyMin INTEGER,
        cpqHeSysUtilPciHour       INTEGER,
        cpqHeSysUtilPciHwLocation DisplayString
    }

    cpqHeSysUtilPciIndex OBJECT-TYPE
        SYNTAX  INTEGER (0..255)
        ACCESS  read-only
        STATUS  mandatory
        DESCRIPTION
            "A unique index into each PCI utilization table entry. "
        ::= { cpqHeSysUtilPciEntry 1 }

    cpqHeSysUtilPciBus OBJECT-TYPE
        SYNTAX  INTEGER (0..255)
        ACCESS  read-only
        STATUS  mandatory
        DESCRIPTION
            "The PCI bus number for this set of utilization numbers. "
        ::= { cpqHeSysUtilPciEntry 2 }

    cpqHeSysUtilPciDevice OBJECT-TYPE
        SYNTAX  INTEGER
        ACCESS  read-only
        STATUS  mandatory
        DESCRIPTION
            "The PCI device number for this set of utilization numbers.
            If this value is -1, the utilization reported is for the
            aggregate of all devices on this PCI bus. "
        ::= { cpqHeSysUtilPciEntry 3 }

    cpqHeSysUtilPciMin OBJECT-TYPE
        SYNTAX  INTEGER
        ACCESS  read-only
        STATUS  mandatory
        DESCRIPTION
            "The utilization as a percentage of the theoretical
            maximum during the last minute.  A value of -1 indicates
            that the utilization number is not available."
        ::= { cpqHeSysUtilPciEntry 4 }

    cpqHeSysUtilPciFiveMin OBJECT-TYPE
        SYNTAX  INTEGER
        ACCESS  read-only
        STATUS  mandatory
        DESCRIPTION
            "The utilization as a percentage of the theoretical
            maximum during the last five minutes.  A value of -1
            indicates that the utilization number is not available."
        ::= { cpqHeSysUtilPciEntry 5 }

    cpqHeSysUtilPciThirtyMin OBJECT-TYPE
        SYNTAX  INTEGER
        ACCESS  read-only
        STATUS  mandatory
        DESCRIPTION
            "The utilization as a percentage of the theoretical
            maximum during the last thirty minutes.  A value of -1
            indicates that the utilization number is not available."
        ::= { cpqHeSysUtilPciEntry 6 }

    cpqHeSysUtilPciHour OBJECT-TYPE
        SYNTAX  INTEGER
        ACCESS  read-only
        STATUS  mandatory
        DESCRIPTION
            "The utilization as a percentage of the theoretical
            maximum during the last hour.  A value of -1 indicates
            that the utilization number is not available."
        ::= { cpqHeSysUtilPciEntry 7 }

    cpqHeSysUtilPciHwLocation OBJECT-TYPE
        SYNTAX  DisplayString (SIZE (0..255))
        ACCESS  read-only
        STATUS  optional
        DESCRIPTION
            "A text description of the hardware location, on complex
             multi SBB hardware only, for the PCI drawer.
             A NULL string indicates that the hardware location could not
             be determined or is irrelevant."
        ::= { cpqHeSysUtilPciEntry 8 }

-- ****************************************************************************
--   Health MIB Fault Tolerant Power Supply Group
--   ============================================
--
-- The compaq enterprise               (1.3.6.1.4.1.232)
--      cpqHealth Group                (1.3.6.1.4.1.232.6)
--       cpqHeComponent Group          (1.3.6.1.4.1.232.6.2)
--        cpqHeFltTolPwrSupply Group   (1.3.6.1.4.1.232.6.2.9)
--
--  The cpqHeFltTolPwrSupply group contains management information about fault
--  tolerant power supplies contained in Compaq Servers.
--
--  Implementation of the cpqHeFltTolPwrSupply group is mandatory for all
--  agents that support the Compaq Health MIB.
--
-- ****************************************************************************
    cpqHeFltTolPwrSupplyCondition OBJECT-TYPE
        SYNTAX  INTEGER {
            other(1),
            ok(2),
            degraded(3),
            failed(4)
            }
        ACCESS  read-only
        STATUS  mandatory
        DESCRIPTION
            "This value specifies the overall condition of the fault tolerant
             power supply sub-system."
        ::= { cpqHeFltTolPwrSupply 1 }

      cpqHeFltTolPwrSupplyStatus OBJECT-TYPE
        SYNTAX  INTEGER {
            other(1),
            notSupported(2),
            notInstalled(3),
            installed(4)
            }
        ACCESS  read-only
        STATUS  mandatory
        DESCRIPTION
            "This value specifies the status of the fault tolerant power
             supply."
        ::= { cpqHeFltTolPwrSupply 2 }

-- ****************************************************************************
--   Health MIB Fault Tolerant Power Supply Table
--   ============================================
--
-- The compaq enterprise               (1.3.6.1.4.1.232)
--      cpqHealth Group                (1.3.6.1.4.1.232.6)
--       cpqHeComponent Group          (1.3.6.1.4.1.232.6.2)
--        cpqHeFltTolPowerSupply Group (1.3.6.1.4.1.232.6.2.9)
--         cpqHeFltTolPowerSupplyTable (1.3.6.1.4.1.232.6.2.9.3)
--
-- ****************************************************************************

    cpqHeFltTolPowerSupplyTable OBJECT-TYPE
        SYNTAX  SEQUENCE OF CpqHeFltTolPowerSupplyEntry
        ACCESS  not-accessible
        STATUS  mandatory
        DESCRIPTION
            "A table of Power Supply Entries."
        ::= { cpqHeFltTolPwrSupply 3 }

    cpqHeFltTolPowerSupplyEntry OBJECT-TYPE
        SYNTAX  CpqHeFltTolPowerSupplyEntry
        ACCESS  not-accessible
        STATUS  mandatory
        DESCRIPTION
            "A Fault Tolerant Power Supply Entry."
        INDEX   { cpqHeFltTolPowerSupplyChassis, cpqHeFltTolPowerSupplyBay }
        ::= { cpqHeFltTolPowerSupplyTable 1 }

    CpqHeFltTolPowerSupplyEntry ::= SEQUENCE {
        cpqHeFltTolPowerSupplyChassis             INTEGER,
        cpqHeFltTolPowerSupplyBay                 INTEGER,
        cpqHeFltTolPowerSupplyPresent             INTEGER,
        cpqHeFltTolPowerSupplyCondition           INTEGER,
        cpqHeFltTolPowerSupplyStatus              INTEGER,
        cpqHeFltTolPowerSupplyMainVoltage         INTEGER,
        cpqHeFltTolPowerSupplyCapacityUsed        INTEGER,
        cpqHeFltTolPowerSupplyCapacityMaximum     INTEGER,
        cpqHeFltTolPowerSupplyRedundant           INTEGER,
        cpqHeFltTolPowerSupplyModel               DisplayString,
        cpqHeFltTolPowerSupplySerialNumber        DisplayString,
        cpqHeFltTolPowerSupplyAutoRev             OCTET STRING,
        cpqHeFltTolPowerSupplyHotPlug             INTEGER,
        cpqHeFltTolPowerSupplyFirmwareRev         DisplayString,
        cpqHeFltTolPowerSupplyHwLocation          DisplayString,
        cpqHeFltTolPowerSupplySparePartNum        DisplayString
    }

    cpqHeFltTolPowerSupplyChassis OBJECT-TYPE
        SYNTAX  INTEGER
        ACCESS  read-only
        STATUS  mandatory
        DESCRIPTION
            "The system chassis number."
        ::= { cpqHeFltTolPowerSupplyEntry 1 }

    cpqHeFltTolPowerSupplyBay OBJECT-TYPE
        SYNTAX  INTEGER
        ACCESS  read-only
        STATUS  mandatory
        DESCRIPTION
            "The bay number to index within this chassis."
        ::= { cpqHeFltTolPowerSupplyEntry 2 }

    cpqHeFltTolPowerSupplyPresent OBJECT-TYPE
        SYNTAX  INTEGER {
            other(1),
            absent(2),
            present(3)
            }
        ACCESS  read-only
        STATUS  mandatory
        DESCRIPTION
            "Indicates whether the power supply is present in the chassis."
        ::= { cpqHeFltTolPowerSupplyEntry 3 }

    cpqHeFltTolPowerSupplyCondition OBJECT-TYPE
        SYNTAX  INTEGER {
            other(1),
            ok(2),
            degraded(3),
            failed(4)
            }
        ACCESS  read-only
        STATUS  mandatory
        DESCRIPTION
            "The condition of the power supply.

            This value will be one of the following:

            other(1)
              The status could not be determined or not present.

            ok(2)
              The power supply is operating normally.

            degraded(3)
              A temperature sensor, fan or other power supply component is
              outside of normal operating range.

            failed(4)
              A power supply component detects a condition that could
              permanently damage the system."
        ::= { cpqHeFltTolPowerSupplyEntry 4 }

    cpqHeFltTolPowerSupplyStatus OBJECT-TYPE
        SYNTAX  INTEGER {
            noError(1),
            generalFailure(2),
            bistFailure(3),
            fanFailure(4),
            tempFailure(5),
            interlockOpen(6),
            epromFailed(7),
            vrefFailed(8),
            dacFailed(9),
            ramTestFailed(10),
            voltageChannelFailed(11),
            orringdiodeFailed(12),
            brownOut(13),
            giveupOnStartup(14),
            nvramInvalid(15),
            calibrationTableInvalid(16)
            }
        ACCESS  read-only
        STATUS  mandatory
        DESCRIPTION
            "The status of the power supply."
        ::= { cpqHeFltTolPowerSupplyEntry 5 }

    cpqHeFltTolPowerSupplyMainVoltage OBJECT-TYPE
        SYNTAX  INTEGER
        ACCESS  read-only
        STATUS  mandatory
        DESCRIPTION
            "The input main voltage of the power supply in volts."
        ::= { cpqHeFltTolPowerSupplyEntry 6 }

    cpqHeFltTolPowerSupplyCapacityUsed OBJECT-TYPE
        SYNTAX  INTEGER
        ACCESS  read-only
        STATUS  mandatory
        DESCRIPTION
            "The currently used capacity of the power supply in watts."
        ::= { cpqHeFltTolPowerSupplyEntry 7 }

    cpqHeFltTolPowerSupplyCapacityMaximum OBJECT-TYPE
        SYNTAX  INTEGER
        ACCESS  read-only
        STATUS  mandatory
        DESCRIPTION
            "The maximum capacity of the power supply in watts."
        ::= { cpqHeFltTolPowerSupplyEntry 8 }

    cpqHeFltTolPowerSupplyRedundant OBJECT-TYPE
        SYNTAX  INTEGER {
            other(1),
            notRedundant(2),
            redundant(3)
            }
        ACCESS  read-only
        STATUS  mandatory
        DESCRIPTION
            "The redundancy state of the power supply.

            This value will be one of the following:
            other(1)
              The redundancy state could not be determined.

            notRedundant(2)
              The power supply is not operating in a redundant state.

            redundant(3)
              The power supply is operating in a redundant state."
        ::= { cpqHeFltTolPowerSupplyEntry 9 }

    cpqHeFltTolPowerSupplyModel OBJECT-TYPE
        SYNTAX  DisplayString (SIZE (0..80))
        ACCESS  read-only
        STATUS  mandatory
        DESCRIPTION
            "The power supply model name."
        ::= { cpqHeFltTolPowerSupplyEntry 10 }

    cpqHeFltTolPowerSupplySerialNumber OBJECT-TYPE
        SYNTAX  DisplayString (SIZE (0..80))
        ACCESS  read-only
        STATUS  mandatory
        DESCRIPTION
            "The power supply serial number."
        ::= { cpqHeFltTolPowerSupplyEntry 11 }

    cpqHeFltTolPowerSupplyAutoRev OBJECT-TYPE
        SYNTAX  OCTET STRING (SIZE (0..4))
        ACCESS  read-only
        STATUS  mandatory
        DESCRIPTION
            "The power supply auto revision number."
        ::= { cpqHeFltTolPowerSupplyEntry 12 }

    cpqHeFltTolPowerSupplyHotPlug OBJECT-TYPE
        SYNTAX  INTEGER {
            other(1),
            nonHotPluggable(2),
            hotPluggable(3)
            }
        ACCESS  read-only
        STATUS  mandatory
        DESCRIPTION
            "This indicates if the power supply is capable of being
            removed and/or inserted while the system is in an operational
            state.

            If the value is hotPluggable(3), the power supply can be safely
            removed if and only if the cpqHeFltTolPowerSupplyRedundant
            field is in a redundant(3) state.

            This value will be one of the following:
            other(1)
              The state could not be determined.

            nonHotPluggable(2)
              The power supply is not hot plug capable.

            hotPluggable(3)
              The power supply is hot plug capable and can be removed if
              the system is operating in a redundant state.  A power
              supply may be added to an empty power supply bay."
        ::= { cpqHeFltTolPowerSupplyEntry 13 }

    cpqHeFltTolPowerSupplyFirmwareRev OBJECT-TYPE
        SYNTAX  DisplayString (SIZE (0..24))
        ACCESS  read-only
        STATUS  mandatory
        DESCRIPTION
            "The power supply firmware revision.  This field will be left
            blank if the firmware revision is unknown."
        ::= { cpqHeFltTolPowerSupplyEntry 14 }

    cpqHeFltTolPowerSupplyHwLocation OBJECT-TYPE
        SYNTAX  DisplayString (SIZE (0..255))
        ACCESS  read-only
        STATUS  optional
        DESCRIPTION
            "A text description of the hardware location, on complex
             multi SBB hardware only, for the power supply.
             A NULL string indicates that the hardware location could not
             be determined or is irrelevant."
        ::= { cpqHeFltTolPowerSupplyEntry 15 }

    cpqHeFltTolPowerSupplySparePartNum OBJECT-TYPE
        SYNTAX  DisplayString (SIZE (0..80))
        ACCESS  read-only
        STATUS  optional
        DESCRIPTION
            "The power supply spare part number."
        ::= { cpqHeFltTolPowerSupplyEntry 16 }



-- ****************************************************************************
--   Health MIB Integrated Remote Console (IRC) Group
--   ================================================
--
-- The compaq enterprise               (1.3.6.1.4.1.232)
--      cpqHealth Group                (1.3.6.1.4.1.232.6)
--       cpqHeComponent Group          (1.3.6.1.4.1.232.6.2)
--        cpqHeIRC Group               (1.3.6.1.4.1.232.6.2.10)
--
--  The cpqHeIRC group contains management information about the Integrated
--  Remote Console ASIC.
--
--  Implementation of the cpqHeIRC group is mandatory for all agents that
--  support the Compaq Health MIB.
--
-- ****************************************************************************

    cpqHeIRCStatus OBJECT-TYPE
        SYNTAX INTEGER {
            unknown(1),
            notavailable(2),
            disabled(3),
            enabled(4)
            }
        ACCESS read-only
        STATUS mandatory
        DESCRIPTION
            "The status of the Integrated Remote Console.  A value of notavailable
             will be returned if this system does not contain IRC."

        ::= { cpqHeIRC 1 }

-- ****************************************************************************
--   Health MIB System Event Log Group
--   =================================
--
-- The compaq enterprise               (1.3.6.1.4.1.232)
--      cpqHealth Group                (1.3.6.1.4.1.232.6)
--       cpqHeComponent Group          (1.3.6.1.4.1.232.6.2)
--        cpqHeEventLog Group          (1.3.6.1.4.1.232.6.2.11)
--
--  The cpqHeEventLog group describes the health system event log.
--
--  Implementation of the cpqHeEventLog group is mandatory for all
--  agents that support the Compaq Health MIB.
--
-- ****************************************************************************

    cpqHeEventLogSupported OBJECT-TYPE
        SYNTAX  INTEGER {
            other(1),
            notSupported(2),
            supported(3)
            }
        ACCESS  read-only
        STATUS  mandatory
        DESCRIPTION
            "This value specifies if this system supports the Integrated
            Management Log feature."
        ::= { cpqHeEventLog 1 }

    cpqHeEventLogCondition OBJECT-TYPE
        SYNTAX  INTEGER {
            other(1),
            ok(2),
            degraded(3),
            failed(4)
            }
        ACCESS  read-only
        STATUS  mandatory
        DESCRIPTION
            "This value specifies the overall condition of the Integrated
            Management Log feature."
        ::= { cpqHeEventLog 2 }

-- ****************************************************************************
--   Health MIB System Event Log Table
--   =================================
--
-- The compaq enterprise               (1.3.6.1.4.1.232)
--      cpqHealth Group                (1.3.6.1.4.1.232.6)
--       cpqHeComponent Group          (1.3.6.1.4.1.232.6.2)
--        cpqHeEventLog Group          (1.3.6.1.4.1.232.6.2.11)
--         cpqHeEventLogTable          (1.3.6.1.4.1.232.6.2.11.3)
--
-- ****************************************************************************

    cpqHeEventLogTable OBJECT-TYPE
        SYNTAX  SEQUENCE OF CpqHeEventLogEntry
        ACCESS  not-accessible
        STATUS  mandatory
        DESCRIPTION
            "A table of System Event Log Entries."
        ::= { cpqHeEventLog 3 }

    cpqHeEventLogEntry OBJECT-TYPE
        SYNTAX  CpqHeEventLogEntry
        ACCESS  not-accessible
        STATUS  mandatory
        DESCRIPTION
            "A System Event Log Entry."
        INDEX   { cpqHeEventLogEntryNumber }
        ::= { cpqHeEventLogTable 1 }

    CpqHeEventLogEntry ::= SEQUENCE {
        cpqHeEventLogEntryNumber         INTEGER,
        cpqHeEventLogEntrySeverity       INTEGER,
        cpqHeEventLogEntryClass          INTEGER,
        cpqHeEventLogEntryCode           INTEGER,
        cpqHeEventLogEntryCount          INTEGER,
        cpqHeEventLogInitialTime         OCTET STRING,
        cpqHeEventLogUpdateTime          OCTET STRING,
        cpqHeEventLogErrorDesc           DisplayString,
        cpqHeEventLogFreeFormData        OCTET STRING
    }

    cpqHeEventLogEntryNumber OBJECT-TYPE
        SYNTAX  INTEGER
        ACCESS  read-only
        STATUS  mandatory
        DESCRIPTION
            "A number that uniquely specifies this system event log
            entry."
        ::= { cpqHeEventLogEntry 1 }

    cpqHeEventLogEntrySeverity OBJECT-TYPE
        SYNTAX  INTEGER {
            informational(2),   -- informational with no action required
            infoWithAlert(3),   -- informational but with LCD alert message
            repaired(6),        -- corrective action taken
            caution(9),         -- non-fatal error condition
            critical(15)        -- component failure
            }
        ACCESS  read-write
        STATUS  mandatory
        DESCRIPTION
            "This value specifies the severity of the event log entry.
            A caution or critical entry can have it's severity
            lowered by setting this variable to the repaired state."
        ::= { cpqHeEventLogEntry 2 }

    cpqHeEventLogEntryClass OBJECT-TYPE
        SYNTAX  INTEGER
        ACCESS  read-only
        STATUS  mandatory
        DESCRIPTION
            "This value specifies the event log entry class designation."
        ::= { cpqHeEventLogEntry 3 }

    cpqHeEventLogEntryCode OBJECT-TYPE
        SYNTAX  INTEGER
        ACCESS  read-only
        STATUS  mandatory
        DESCRIPTION
            "This value specifies the event log entry code designation.
            The meaning of this changes depending on the class."
        ::= { cpqHeEventLogEntry 4 }

    cpqHeEventLogEntryCount OBJECT-TYPE
        SYNTAX  INTEGER
        ACCESS  read-only
        STATUS  mandatory
        DESCRIPTION
            "This value specifies the event log entry occurrence count.
            This represents the number of times this event has occurred
            starting from the initial time until the last modified time."
        ::= { cpqHeEventLogEntry 5 }

    cpqHeEventLogInitialTime OBJECT-TYPE
        SYNTAX  OCTET STRING (SIZE (6))
        ACCESS  read-only
        STATUS  mandatory
        DESCRIPTION
            "The time stamp when the event log entry was first created.

             field  octets  contents                  range
             =====  ======  ========                  =====
               1      1-2   year                      0..65536
               2       3    month                     1..12
               3       4    day                       1..31
               4       5    hour                      0..23
               5       6    minute                    0..59

            The year field is set with the most significant octet first.
            A value of 0 in the year indicates an unknown time stamp."
        ::= { cpqHeEventLogEntry 6 }

    cpqHeEventLogUpdateTime OBJECT-TYPE
        SYNTAX  OCTET STRING (SIZE (6))
        ACCESS  read-only
        STATUS  mandatory
        DESCRIPTION
            "The time stamp when the event log entry was last modified.

             field  octets  contents                  range
             =====  ======  ========                  =====
               1      1-2   year                      0..65536
               2       3    month                     1..12
               3       4    day                       1..31
               4       5    hour                      0..23
               5       6    minute                    0..59

            The year field is set with the most significant octet first.
            A value of 0 in the year indicates an unknown time stamp."
        ::= { cpqHeEventLogEntry 7 }

    cpqHeEventLogErrorDesc OBJECT-TYPE
        SYNTAX  DisplayString (SIZE (0..255))
        ACCESS  read-only
        STATUS  mandatory
        DESCRIPTION
            "A text description of the event log entry."
        ::= { cpqHeEventLogEntry 8 }

    cpqHeEventLogFreeFormData OBJECT-TYPE
        SYNTAX  OCTET STRING (SIZE (0..128))
        ACCESS  read-only
        STATUS  mandatory
        DESCRIPTION
            "This is the free form data associated with a particular
            event."
        ::= { cpqHeEventLogEntry 9 }

-- ****************************************************************************
--   Health MIB Management Display Group
--   ===================================
--
-- The compaq enterprise               (1.3.6.1.4.1.232)
--      cpqHealth Group                (1.3.6.1.4.1.232.6)
--       cpqHeComponent Group          (1.3.6.1.4.1.232.6.2)
--        cpqHeMgmtDisplay Group       (1.3.6.1.4.1.232.6.2.12)
--
-- ****************************************************************************

--  The cpqHeMgmtDisplay group maintains information about the Management
--  Display device.
--
--  Implementation of the cpqHeTrap group is mandatory for agents that
--  support the Compaq Health MIB.

    cpqHeMgmtDisplayType OBJECT-TYPE
        SYNTAX  INTEGER {
            other(1),            -- Unknown device or could not be determined
            none(2),             -- No Management display device
            imd4x16(3),          -- Compaq IMD display (4 lines by 16 chars)
            ocp1x16(4)           -- Digital OCP display (1 line by 16 chars)
            }
        ACCESS  read-only
        STATUS  mandatory
        DESCRIPTION
            "This value specifies the type of Management Display device.
            If a display device is available on the server, the type
            will be set accordingly.  If no device is present, the value
            will be set to none(2)."
        ::= { cpqHeMgmtDisplay 1 }

    cpqHeMgmtDisplayText OBJECT-TYPE
        SYNTAX  DisplayString (SIZE (0..255))
        ACCESS  read-write
        STATUS  mandatory
        DESCRIPTION
            "The text to be written to the Management display device.

            If this item is read, it may not accurately reflect what
            is currently displayed."
        ::= { cpqHeMgmtDisplay 2 }

    cpqHeMgmtUID OBJECT-TYPE
        SYNTAX  INTEGER {
            other(1),            -- Unknown device or could not be determined
            none(2),             -- No unit identifier device
            ledOn(3),            -- Unit identifier LED is On
            ledOff(4),           -- Unit identifier LED is Off
            ledBlinking(5)       -- Unit identifier LED is Blinking
            }
        ACCESS  read-write
        STATUS  mandatory
        DESCRIPTION
            "The Unit Identifer LED.

            This value will be one of the following:

            other(1)
              The state of the LED could not be determined.  Setting the
              LED state is not allowed.

            none(2)
              The LED is not present.  Setting LED state is not allowed.

            ledOn(3)
              The LED is present and ON.  The LED can be turned Off or Blinking
              by setting the cpqHeMgmtUID to ledOff(4) or ledBlinking(5) respectively.

            ledOff(4)
              The LED is present and OFF.  The LED can be turned On or Blinking
              by setting the cpqHeMgmtUID to ledOn(3) or ledBlinking(5) respectively.

            ledBlinking(5)
              The LED is present and is Blinking.  The LED can be turned On or Off
              by setting the cpqHeMgmtUID to ledOn(3) or ledOff(4) respectively"
        ::= { cpqHeMgmtDisplay 3 }

-- ****************************************************************************
--   Health MIB Power Converter Group
--   ================================
--
-- The compaq enterprise               (1.3.6.1.4.1.232)
--      cpqHealth Group                (1.3.6.1.4.1.232.6)
--       cpqHeComponent Group          (1.3.6.1.4.1.232.6.2)
--        cpqHePowerConverter Group    (1.3.6.1.4.1.232.6.2.13)
--
--  The cpqHePowerConverter group describes the power converter modules
--  in the system.
--
--  Implementation of the cpqHePowerConverter group is mandatory for all
--  agents that support the Compaq Health MIB.
--
-- ****************************************************************************

    cpqHePowerConverterSupported OBJECT-TYPE
        SYNTAX  INTEGER {
            other(1),
            notSupported(2),
            supported(3)
            }
        ACCESS  read-only
        STATUS  mandatory
        DESCRIPTION
            "This value specifies if this system supports reporting
            power converter module information."
        ::= { cpqHePowerConverter 1 }

    cpqHePowerConverterCondition OBJECT-TYPE
        SYNTAX  INTEGER {
            other(1),
            ok(2),
            degraded(3),
            failed(4)
            }
        ACCESS  read-only
        STATUS  mandatory
        DESCRIPTION
            "This value specifies the overall condition of the power
            converters modules in the system."
        ::= { cpqHePowerConverter 2 }

-- ****************************************************************************
--   Health MIB Power Converter Table
--   ================================
--
-- The compaq enterprise               (1.3.6.1.4.1.232)
--      cpqHealth Group                (1.3.6.1.4.1.232.6)
--       cpqHeComponent Group          (1.3.6.1.4.1.232.6.2)
--        cpqHePowerConverter Group    (1.3.6.1.4.1.232.6.2.13)
--         cpqHePowerConverterTable    (1.3.6.1.4.1.232.6.2.13.3)
--
-- ****************************************************************************

    cpqHePowerConverterTable OBJECT-TYPE
        SYNTAX  SEQUENCE OF CpqHePowerConverterEntry
        ACCESS  not-accessible
        STATUS  mandatory
        DESCRIPTION
            "A table of Power Converter Module Entries."
        ::= { cpqHePowerConverter 3 }

    cpqHePowerConverterEntry OBJECT-TYPE
        SYNTAX  CpqHePowerConverterEntry
        ACCESS  not-accessible
        STATUS  mandatory
        DESCRIPTION
            "A Power Converter Module Entry."
        INDEX   { cpqHePwrConvChassis, cpqHePwrConvIndex }
        ::= { cpqHePowerConverterTable 1 }

    CpqHePowerConverterEntry ::= SEQUENCE {
        cpqHePwrConvChassis             INTEGER,
        cpqHePwrConvIndex               INTEGER,
        cpqHePwrConvPresent             INTEGER,
        cpqHePwrConvSlot                INTEGER,
        cpqHePwrConvSocket              INTEGER,
        cpqHePwrConvRedundant           INTEGER,
        cpqHePwrConvRedundantGroupId    INTEGER,
        cpqHePwrConvCondition           INTEGER,
        cpqHePwrConvHwLocation          DisplayString
    }

    cpqHePwrConvChassis OBJECT-TYPE
        SYNTAX  INTEGER
        ACCESS  read-only
        STATUS  mandatory
        DESCRIPTION
            "The system chassis number containing the power converter
            modules."
        ::= { cpqHePowerConverterEntry 1 }

    cpqHePwrConvIndex OBJECT-TYPE
        SYNTAX  INTEGER
        ACCESS  read-only
        STATUS  mandatory
        DESCRIPTION
            "The Power Converter Module number to index within the chassis."
        ::= { cpqHePowerConverterEntry 2 }

    cpqHePwrConvPresent OBJECT-TYPE
        SYNTAX  INTEGER {
            other(1),
            absent(2),
            present(3)
            }
        ACCESS  read-only
        STATUS  mandatory
        DESCRIPTION
            "This specifies if the Power Converter Module described is
            present in the system."
        ::= { cpqHePowerConverterEntry 3 }

    cpqHePwrConvSlot OBJECT-TYPE
        SYNTAX  INTEGER
        ACCESS  read-only
        STATUS  mandatory
        DESCRIPTION
            "The Power Converter Module slot number within the chassis."
        ::= { cpqHePowerConverterEntry 4 }

    cpqHePwrConvSocket OBJECT-TYPE
        SYNTAX  INTEGER
        ACCESS  read-only
        STATUS  mandatory
        DESCRIPTION
            "The Power Converter Module socket number within the slot."
        ::= { cpqHePowerConverterEntry 5 }

    cpqHePwrConvRedundant OBJECT-TYPE
        SYNTAX  INTEGER {
            other(1),
            nonRedundant(2),
            redundant(3)
            }
        ACCESS  read-only
        STATUS  mandatory
        DESCRIPTION
            "This specifies if the Power Converter Module is redundant."
        ::= { cpqHePowerConverterEntry 6 }

    cpqHePwrConvRedundantGroupId OBJECT-TYPE
        SYNTAX  INTEGER
        ACCESS  read-only
        STATUS  mandatory
        DESCRIPTION
            "The Power Converter Module group id.  A redundant set of
            power converters will have the same group id."
        ::= { cpqHePowerConverterEntry 7 }

    cpqHePwrConvCondition OBJECT-TYPE
        SYNTAX  INTEGER {
            other(1),
            ok(2),
            degraded(3),
            failed(4)
            }
        ACCESS  read-only
        STATUS  mandatory
        DESCRIPTION
            "The Power Converter Module condition."
        ::= { cpqHePowerConverterEntry 8 }

    cpqHePwrConvHwLocation OBJECT-TYPE
        SYNTAX  DisplayString (SIZE (0..255))
        ACCESS  read-only
        STATUS  optional
        DESCRIPTION
            "A text description of the hardware location, on complex
             multi SBB hardware only, for the power converter.
             A NULL string indicates that the hardware location could not
             be determined or is irrelevant."
        ::= { cpqHePowerConverterEntry 9 }

-- ****************************************************************************
--   Health MIB Resilient Memory Group
--   =================================
--
-- The compaq enterprise               (1.3.6.1.4.1.232)
--      cpqHealth Group                (1.3.6.1.4.1.232.6)
--       cpqHeComponent Group          (1.3.6.1.4.1.232.6.2)
--        cpqHeResilientMemory Group   (1.3.6.1.4.1.232.6.2.14)
--
--  The cpqHeResilientMemory group describes the Resilient Memory sub-system
--  in the server.
--
--
--  Implementation of the cpqHeResilientMemory group is mandatory for all
--  Server Agents that support the Compaq Health MIB.
--
-- ****************************************************************************


    cpqHeResilientMemTypeActive OBJECT-TYPE
        SYNTAX  INTEGER {
            other(1),
            none(2),
            onLineSpare(3)
            }
        ACCESS  read-only
        STATUS  mandatory
        DESCRIPTION
            "This value specifies the type of Resilient Memory fault
            tolerance currently active on the system.

            The following connection states are supported:

            other(1)
              The Resilient Memory fault tolerance cannot be determined
              by the Management Agent.  You may need to upgrade your
              software.

            none(2)
              This system is not configured for Resilient Memory
              fault tolerance.

            onLineSpare(3)
              This system is configured for Online Spare Resilient Memory."
        ::= { cpqHeResilientMemory 1 }

    cpqHeResilientMemTypeAvailable OBJECT-TYPE
        SYNTAX  INTEGER
        ACCESS  read-only
        STATUS  mandatory
        DESCRIPTION
            "This value specifies the type of Resilient Memory Fault
            Tolerance available on the system.

            This is a collection of flags used to indicate the fault
            Resilient Memory options available. This integer is a bitmap,
            with each bit indicating the availability of an option. If
            the bit is set to 1, the option is available; otherwise it
            is not. Multiple options are allowed.

            NOTE:   bit 31 is the most significant bit, bit 0 is the least
                    significant.

                    Bit 31-1:  RESERVED
                    Bit 0:     Online Spare"
        ::= { cpqHeResilientMemory 2 }

    cpqHeResilientMemStatus OBJECT-TYPE
        SYNTAX  INTEGER {
            other(1),
            notProtected(2),
            protected(3),
            degraded(4)
            }
        ACCESS  read-only
        STATUS  mandatory
        DESCRIPTION
            "This value specifies the current state of the Resilient
            Memory subsystem.

            The following states are supported:

            other(1)
              The system does not support Resilient Memory or the
              status cannot be determined by the Management Agent.

            notProtected(2)
              This system supports Resilient Memory but the
              feature is disabled.

            protected(3)
              The system is protected.

            degraded(4)
              The system was protected, but the Resilient Memory
              has been engaged."
        ::= { cpqHeResilientMemory 3 }

    cpqHeResilientMemCondition OBJECT-TYPE
        SYNTAX  INTEGER {
            other(1),
            ok(2),
            degraded(3)
            }
        ACCESS  read-only
        STATUS  mandatory
        DESCRIPTION
            "This value specifies the current condition of the Resilient
            Memory subsystem.

            The following states are supported:

            other(1)
              The system does not support fault tolerant memory or the
              state cannot be determined by the Management Agent.

            ok(2)
              This system is operating normally.

            degraded(3)
              The system is running in a degraded state because the
              Resilient Memory subsystem has been engaged."
        ::= { cpqHeResilientMemory 4 }


-- ****************************************************************************
--   HealthMIB Trap Group
--   =====================
--
-- The compaq enterprise               (1.3.6.1.4.1.232)
--      cpqHealth Group                (1.3.6.1.4.1.232.6)
--       cpqHeTrap Group               (1.3.6.1.4.1.232.6.3)  (deprecated)
--
--  The cpqHeTrap group maintains information about the number of traps
--  issued from the health enterprise.  The trap group also maintains a table
--  of the last several traps issued.  This table is intended to give a
--  management application some recent status information immediately upon
--  accessing the agent.
--
--  Implementation of the cpqHeTrap group is optional for agents that
--  support the Compaq Health MIB.
--
-- ****************************************************************************

    cpqHeTrapPkts OBJECT-TYPE
        SYNTAX  Counter
        ACCESS  read-only
        STATUS  deprecated
        DESCRIPTION
            "The total number of SNMP trap packets issued by the Compaq
            Server Health agent."
        ::= { cpqHeTrap 1 }

    cpqHeTrapLogMaxSize OBJECT-TYPE
        SYNTAX  INTEGER (0..2147483647)
        ACCESS  read-only
        STATUS  deprecated
        DESCRIPTION
            "The maximum number of entries that will currently be kept in
            the trap log.  If the maximum size has been reached and a new
            trap occurs the oldest trap will be removed."
        ::= { cpqHeTrap 2 }

-- ****************************************************************************
--   Health MIB Trap Log Table
--   =========================
--
-- The compaq enterprise               (1.3.6.1.4.1.232)
--      cpqHealth Group                (1.3.6.1.4.1.232.6)
--       cpqHeTrap Group               (1.3.6.1.4.1.232.6.3)
--        cpqHeTrapLogTable            (1.3.6.1.4.1.232.6.3.3)  (deprecated)
--
-- ****************************************************************************

    cpqHeTrapLogTable OBJECT-TYPE
        SYNTAX  SEQUENCE OF CpqHeTrapLogEntry
        ACCESS  not-accessible
        STATUS  deprecated
        DESCRIPTION
            "An ordered list of trap log entries (conceptually a queue).  The
            trap log entries will be kept in the order in which they were
            generated with the most recent trap at index 1 and the oldest
            trap entry at index trapLogMaxSize.  If the maximum number of
            entries has been reached and a new trap occurs the oldest trap
            will be removed when the new trap is added so the trapMaxLogSize
            is not exceeded."
        ::= { cpqHeTrap 3 }

    cpqHeTrapLogEntry OBJECT-TYPE
        SYNTAX  CpqHeTrapLogEntry
        ACCESS  not-accessible
        STATUS  deprecated
        DESCRIPTION
            "A description of a trap event."
        INDEX   { cpqHeTrapLogIndex }
        ::= { cpqHeTrapLogTable 1 }

    CpqHeTrapLogEntry ::= SEQUENCE {
        cpqHeTrapLogIndex        INTEGER,
        cpqHeTrapType            INTEGER,
        cpqHeTrapTime            OCTET STRING
    }

    cpqHeTrapLogIndex OBJECT-TYPE
        SYNTAX  INTEGER (0..2147483647)
        ACCESS  read-only
        STATUS  deprecated
        DESCRIPTION
            "The value of this object uniquely identifies this trapLogEntry
             at this time.  The most recent trap will have an index of 1 and
             the oldest trap will have an index of trapLogMaxSize.  Because of
             the queue-like nature of the trapLog this particular trap event's
             index will change as new traps are issued."
        ::= { cpqHeTrapLogEntry 1 }

    cpqHeTrapType OBJECT-TYPE
        SYNTAX  INTEGER {
            cpqHeCorrectableMemoryError(1),
            cpqHeCorrectableMemoryLogDisabled(2),
            cpqHe2CorrectableMemoryError(6001),
            cpqHe2CorrectableMemoryLogDisabled(6002),
            cpqHeThermalTempFailed(6003),
            cpqHeThermalTempDegraded(6004),
            cpqHeThermalTempOk(6005),
            cpqHeThermalSystemFanFailed(6006),
            cpqHeThermalSystemFanDegraded(6007),
            cpqHeThermalSystemFanOk(6008),
            cpqHeThermalCpuFanFailed(6009),
            cpqHeThermalCpuFanOk(6010),
            cpqHeAsrConfirmation(6011),
            cpqHeThermalConfirmation(6012),
            cpqHePostError(6013)
            }
        ACCESS  read-only
        STATUS  deprecated
        DESCRIPTION
            "The type of the trap event this entry describes.  This
             number refers to an entry in a list of traps enumerating the
             possible traps the Compaq Server Health agent may issue."
        ::= { cpqHeTrapLogEntry 2 }

    cpqHeTrapTime OBJECT-TYPE
        SYNTAX  OCTET STRING (SIZE (0..6))
        ACCESS  read-only
        STATUS  deprecated
        DESCRIPTION
            "The time of the trap event that this entry describes.  The time
             is given in year (first octet), month, day of month, hour,
             minute, second (last octet) order.  The octets are in Binary
             Coded Decimal (BCD)."
        ::= { cpqHeTrapLogEntry 3 }

-- ****************************************************************************
--  Health MIB Trap Definitions
--  ===========================
--
--  The SNMP trap messages must not be bigger than 484 octets (bytes).
--
--  Trap support in an SNMP agent implementation is optional.  An SNMP
--  agent implementation may support all, some, or none of the traps.
--  If traps are supported, The user should be provided with the option of
--  disabling traps.
-- **************************************************************************

    cpqHeCorrectableMemoryError TRAP-TYPE
        ENTERPRISE cpqHealth
        VARIABLES  { cpqHeCorrMemTotalErrs }
        DESCRIPTION
            "A correctable memory error occurred.

             The error has been corrected.  The current number of correctable
             memory errors is reported in the variable cpqHeCorrMemTotalErrs."

        --#TYPE "Correctable Memory Error Occurred"
        --#SUMMARY "Total correctable errors = %d."
        --#ARGUMENTS {0}
        --#SEVERITY MINOR
        --#TIMEINDEX 99
        --#STATE   OPERATIONAL

        ::= 1

    cpqHeCorrectableMemoryLogDisabled TRAP-TYPE
        ENTERPRISE cpqHealth
        VARIABLES  { cpqHeCorrMemLogStatus }
        DESCRIPTION
            "Correctable memory error tracking disabled.

             The frequency of errors is so high that the error tracking
             logic has been temporarily disabled.  The cpqHeCorrMemLogStatus
             variable indicated the current tracking status."

        --#TYPE "Memory Error Tracking Disabled"
        --#SUMMARY "Too many memory errors - tracking now disabled."
        --#ARGUMENTS {}
        --#SEVERITY CRITICAL
        --#TIMEINDEX 99
        --#STATE   DEGRADED

        ::= 2

-- Trap definitions for Insight Manager version 2.00 and greater
-- use the Compaq Enterprise (232) and have unique trap numbers between all
-- of the Compaq MIBs.

    cpqHe2CorrectableMemoryError TRAP-TYPE
        ENTERPRISE compaq
        VARIABLES  { cpqHeCorrMemTotalErrs }
        DESCRIPTION
            "A correctable memory error occurred.

             The error has been corrected.  The current number of correctable
             memory errors is reported in the variable cpqHeCorrMemTotalErrs."

        --#TYPE "Correctable Memory Error Occurred"
        --#SUMMARY "Total correctable errors = %d."
        --#ARGUMENTS {0}
        --#SEVERITY MINOR
        --#TIMEINDEX 99
        --#STATE   DEGRADED

        ::= 6001

    cpqHe2CorrectableMemoryLogDisabled TRAP-TYPE
        ENTERPRISE compaq
        VARIABLES  { cpqHeCorrMemLogStatus }
        DESCRIPTION
            "Correctable memory error tracking disabled.

             The frequency of errors is so high that the error tracking
             logic has been temporarily disabled.  The cpqHeCorrMemLogStatus
             variable indicated the current tracking status."

        --#TYPE "Memory Error Tracking Disabled"
        --#SUMMARY "Too many memory errors - tracking now disabled."
        --#ARGUMENTS {}
        --#SEVERITY CRITICAL
        --#TIMEINDEX 99
        --#STATE   DEGRADED

        ::= 6002

    cpqHeThermalTempFailed TRAP-TYPE
        ENTERPRISE compaq
        DESCRIPTION
            "The temperature status has been set to failed.

             The system will be shutdown due to this thermal condition."

        --#TYPE "Thermal Failure"
        --#SUMMARY "System will be shutdown due to this thermal condition."
        --#ARGUMENTS {}
        --#SEVERITY CRITICAL
        --#TIMEINDEX 99
        --#STATE  DEGRADED

        ::= 6003

    cpqHeThermalTempDegraded TRAP-TYPE
        ENTERPRISE compaq
        VARIABLES  { cpqHeThermalDegradedAction }
        DESCRIPTION
            "The temperature status has been set to degraded.

             The server's temperature is outside of the normal operating
             range.  The server will be shutdown if the
             cpqHeThermalDegradedAction variable is set to shutdown(3)."

        --#TYPE "Thermal Status Degraded"
        --#SUMMARY "Temperature out of range.  Shutdown may occur."
        --#ARGUMENTS {}
        --#SEVERITY CRITICAL
        --#TIMEINDEX 99
        --#STATE   DEGRADED

        ::= 6004

    cpqHeThermalTempOk TRAP-TYPE
        ENTERPRISE compaq
        DESCRIPTION
            "The temperature status has been set to ok.

             The server's temperature has returned to the normal operating
             range."

        --#TYPE "Temperature OK"
        --#SUMMARY "Temperature has returned to normal range."
        --#ARGUMENTS {}
        --#SEVERITY INFORMATIONAL
        --#TIMEINDEX 99
        --#STATE OPERATIONAL

        ::= 6005

    cpqHeThermalSystemFanFailed TRAP-TYPE
        ENTERPRISE compaq
        VARIABLES  { cpqHeThermalDegradedAction }
        DESCRIPTION
            "The system fan status has been set to failed.

             A required system fan is not operating normally.  The system
             will be shutdown if the cpqHeThermalDegradedAction variable
             is set to shutdown(3)."

        --#TYPE "System Fan Failure"
        --#SUMMARY "Required fan not operating normally.  Shutdown may occur."
        --#ARGUMENTS {}
        --#SEVERITY CRITICAL
        --#TIMEINDEX 99
        --#STATE   DEGRADED

        ::= 6006

    cpqHeThermalSystemFanDegraded TRAP-TYPE
        ENTERPRISE compaq
        DESCRIPTION
            "The system fan status has been set to degraded.

             An optional system fan is not operating normally."

        --#TYPE "System Fan Degraded"
        --#SUMMARY "An optional fan is not operating normally."
        --#ARGUMENTS {}
        --#SEVERITY CRITICAL
        --#TIMEINDEX 99
        --#STATE   DEGRADED

        ::= 6007

    cpqHeThermalSystemFanOk TRAP-TYPE
        ENTERPRISE compaq
        DESCRIPTION
            "The system fan status has been set to ok.

             Any previously non-operational system fans have returned to
             normal operation."

        --#TYPE "System Fan OK"
        --#SUMMARY "System fan has returned to normal operation."
        --#ARGUMENTS {}
        --#SEVERITY INFORMATIONAL
        --#TIMEINDEX 99
        --#STATE OPERATIONAL

        ::= 6008

    cpqHeThermalCpuFanFailed TRAP-TYPE
        ENTERPRISE compaq
        DESCRIPTION
            "The CPU fan status has been set to failed.

             A processor fan is not operating normally.  The server will be
             shutdown."

        --#TYPE "CPU Fan Failure"
        --#SUMMARY "CPU fan has failed.  Server will be shutdown."
        --#ARGUMENTS {}
        --#SEVERITY CRITICAL
        --#TIMEINDEX 99
        --#STATE   NONOPERATIONAL

        ::= 6009

    cpqHeThermalCpuFanOk TRAP-TYPE
        ENTERPRISE compaq
        DESCRIPTION
            "The CPU fan status has been set to ok.

             Any previously non-operational processor fans have returned
             to normal operation."

        --#TYPE "CPU Fan OK"
        --#SUMMARY "CPU fan is now OK."
        --#ARGUMENTS {}
        --#SEVERITY INFORMATIONAL
        --#TIMEINDEX 99
        --#STATE OPERATIONAL

        ::= 6010

    cpqHeAsrConfirmation TRAP-TYPE
        ENTERPRISE compaq
        DESCRIPTION
            "The server is operational again.

             The server has previously been shutdown by the Compaq
             Automatic Server Recovery (ASR) feature and has just
             become operational again."

        --#TYPE "Server Operational"
        --#SUMMARY "Server is operational again after ASR shutdown."
        --#ARGUMENTS {}
        --#SEVERITY MINOR
        --#TIMEINDEX 99
        --#STATE OPERATIONAL

        ::= 6011

    cpqHeThermalConfirmation TRAP-TYPE
        ENTERPRISE compaq
        DESCRIPTION
            "The server is operational again.

             The server has previously been shutdown due to a thermal
             anomaly on the server and has just become operational again."

        --#TYPE "Server Operational"
        --#SUMMARY "Server is operational again after thermal shutdown."
        --#ARGUMENTS {}
        --#SEVERITY MINOR
        --#TIMEINDEX 99
        --#STATE OPERATIONAL

        ::= 6012

    cpqHePostError TRAP-TYPE
        ENTERPRISE compaq
        DESCRIPTION
            "One or more POST errors occurred.

             Power On Self-Test (POST) errors occur during the server
             restart process.  "

        --#TYPE "POST Errors Occurred"
        --#SUMMARY "Errors occurred during server restart."
        --#ARGUMENTS {}
        --#SEVERITY MINOR
        --#TIMEINDEX 99
        --#STATE OPERATIONAL

        ::= 6013

    cpqHeFltTolPwrSupplyDegraded TRAP-TYPE
        ENTERPRISE compaq
        DESCRIPTION
            "The fault tolerant power supply sub-system condition has been
             set to degraded."

        --#TYPE "Server Power Supply Degraded"
        --#SUMMARY "The server power supply status has become degraded."
        --#ARGUMENTS {}
        --#SEVERITY CRITICAL
        --#TIMEINDEX 99
        --#STATE   DEGRADED

        ::= 6014


    cpqHe3CorrectableMemoryError TRAP-TYPE
        ENTERPRISE compaq
        VARIABLES  { sysName, cpqHoTrapFlags, cpqHeCorrMemTotalErrs }
        DESCRIPTION
            "A correctable memory error occurred.

             The error has been corrected.  The current number of correctable
             memory errors is reported in the variable cpqHeCorrMemTotalErrs."

        --#TYPE "Correctable Memory Error Occurred"
        --#SUMMARY "Total correctable errors = %d."
        --#ARGUMENTS {2}
        --#SEVERITY MINOR
        --#TIMEINDEX 99
        --#STATE   DEGRADED


        ::= 6015

    cpqHe3CorrectableMemoryLogDisabled TRAP-TYPE
        ENTERPRISE compaq
        VARIABLES  { sysName, cpqHoTrapFlags, cpqHeCorrMemLogStatus }
        DESCRIPTION
            "Correctable memory error tracking disabled.

             The frequency of errors is so high that the error tracking
             logic has been temporarily disabled.  The cpqHeCorrMemLogStatus
             variable indicated the current tracking status."

        --#TYPE "Memory Error Tracking Disabled"
        --#SUMMARY "Too many memory errors - tracking now disabled."
        --#ARGUMENTS {}
        --#SEVERITY CRITICAL
        --#TIMEINDEX 99
        --#STATE   DEGRADED

        ::= 6016

    cpqHe3ThermalTempFailed TRAP-TYPE
        ENTERPRISE compaq
        VARIABLES  { sysName, cpqHoTrapFlags }
        DESCRIPTION
            "The temperature status has been set to failed.

             The system will be shutdown due to this thermal condition."

        --#TYPE "Thermal Failure"
        --#SUMMARY "System will be shutdown due to this thermal condition."
        --#ARGUMENTS {}
        --#SEVERITY CRITICAL
        --#TIMEINDEX 99
        --#STATE  DEGRADED

        ::= 6017

    cpqHe3ThermalTempDegraded TRAP-TYPE
        ENTERPRISE compaq
        VARIABLES  { sysName, cpqHoTrapFlags, cpqHeThermalDegradedAction }
        DESCRIPTION
            "The temperature status has been set to degraded.

             The server's temperature is outside of the normal operating
             range.  The server will be shutdown if the
             cpqHeThermalDegradedAction variable is set to shutdown(3)."

        --#TYPE "Thermal Status Degraded"
        --#SUMMARY "Temperature out of range.  Shutdown may occur."
        --#ARGUMENTS {}
        --#SEVERITY CRITICAL
        --#TIMEINDEX 99
        --#STATE   DEGRADED

        ::= 6018

    cpqHe3ThermalTempOk TRAP-TYPE
        ENTERPRISE compaq
        VARIABLES  { sysName, cpqHoTrapFlags }
        DESCRIPTION
            "The temperature status has been set to ok.

             The server's temperature has returned to the normal operating
             range."

        --#TYPE "Temperature OK"
        --#SUMMARY "Temperature has returned to normal range."
        --#ARGUMENTS {}
        --#SEVERITY INFORMATIONAL
        --#TIMEINDEX 99
        --#STATE OPERATIONAL

        ::= 6019

    cpqHe3ThermalSystemFanFailed TRAP-TYPE
        ENTERPRISE compaq
        VARIABLES  { sysName, cpqHoTrapFlags, cpqHeThermalDegradedAction }
        DESCRIPTION
            "The system fan status has been set to failed.

             A required system fan is not operating normally.  The system
             will be shutdown if the cpqHeThermalDegradedAction variable
             is set to shutdown(3)."

        --#TYPE "System Fan Failure"
        --#SUMMARY "Required fan not operating normally.  Shutdown may occur."
        --#ARGUMENTS {}
        --#SEVERITY CRITICAL
        --#TIMEINDEX 99
        --#STATE   DEGRADED

        ::= 6020

    cpqHe3ThermalSystemFanDegraded TRAP-TYPE
        ENTERPRISE compaq
        VARIABLES  { sysName, cpqHoTrapFlags }
        DESCRIPTION
            "The system fan status has been set to degraded.

             An optional system fan is not operating normally."

        --#TYPE "System Fan Degraded"
        --#SUMMARY "An optional fan is not operating normally."
        --#ARGUMENTS {}
        --#SEVERITY CRITICAL
        --#TIMEINDEX 99
        --#STATE   DEGRADED

        ::= 6021

    cpqHe3ThermalSystemFanOk TRAP-TYPE
        ENTERPRISE compaq
        VARIABLES  { sysName, cpqHoTrapFlags }
        DESCRIPTION
            "The system fan status has been set to ok.

             Any previously non-operational system fans have returned to
             normal operation."

        --#TYPE "System Fan OK"
        --#SUMMARY "System fan has returned to normal operation."
        --#ARGUMENTS {}
        --#SEVERITY INFORMATIONAL
        --#TIMEINDEX 99
        --#STATE OPERATIONAL

        ::= 6022

    cpqHe3ThermalCpuFanFailed TRAP-TYPE
        ENTERPRISE compaq
        VARIABLES  { sysName, cpqHoTrapFlags }
        DESCRIPTION
            "The CPU fan status has been set to failed.

             A processor fan is not operating normally.  The server will be
             shutdown."

        --#TYPE "CPU Fan Failure"
        --#SUMMARY "CPU fan has failed.  Server will be shutdown."
        --#ARGUMENTS {}
        --#SEVERITY CRITICAL
        --#TIMEINDEX 99
        --#STATE   NONOPERATIONAL

        ::= 6023

    cpqHe3ThermalCpuFanOk TRAP-TYPE
        ENTERPRISE compaq
        VARIABLES  { sysName, cpqHoTrapFlags }
        DESCRIPTION
            "The CPU fan status has been set to ok.

             Any previously non-operational processor fans have returned
             to normal operation."

        --#TYPE "CPU Fan OK"
        --#SUMMARY "CPU fan is now OK."
        --#ARGUMENTS {}
        --#SEVERITY INFORMATIONAL
        --#TIMEINDEX 99
        --#STATE OPERATIONAL

        ::= 6024

    cpqHe3AsrConfirmation TRAP-TYPE
        ENTERPRISE compaq
        VARIABLES  { sysName, cpqHoTrapFlags }
        DESCRIPTION
            "The server is operational again.

             The server has previously been shutdown by the Compaq
             Automatic Server Recovery (ASR) feature and has just
             become operational again."

        --#TYPE "Server Operational"
        --#SUMMARY "Server is operational again after ASR shutdown."
        --#ARGUMENTS {}
        --#SEVERITY MINOR
        --#TIMEINDEX 99
        --#STATE OPERATIONAL

        ::= 6025

    cpqHe3ThermalConfirmation TRAP-TYPE
        ENTERPRISE compaq
        VARIABLES  { sysName, cpqHoTrapFlags }
        DESCRIPTION
            "The server is operational again.

             The server has previously been shutdown due to a thermal
             anomaly on the server and has just become operational again."

        --#TYPE "Server Operational"
        --#SUMMARY "Server is operational again after thermal shutdown."
        --#ARGUMENTS {}
        --#SEVERITY MINOR
        --#TIMEINDEX 99
        --#STATE OPERATIONAL

        ::= 6026

    cpqHe3PostError TRAP-TYPE
        ENTERPRISE compaq
        VARIABLES  { sysName, cpqHoTrapFlags }
        DESCRIPTION
            "One or more POST errors occurred.

             Power On Self-Test (POST) errors occur during the server
             restart process.  "

        --#TYPE "POST Errors Occurred"
        --#SUMMARY "Errors occurred during server restart."
        --#ARGUMENTS {}
        --#SEVERITY MINOR
        --#TIMEINDEX 99
        --#STATE OPERATIONAL

        ::= 6027

    cpqHe3FltTolPwrSupplyDegraded TRAP-TYPE
        ENTERPRISE compaq
        VARIABLES  { sysName, cpqHoTrapFlags }
        DESCRIPTION
            "The fault tolerant power supply sub-system condition has been
             set to degraded."

        --#TYPE "Server Power Supply Degraded"
        --#SUMMARY "The server power supply status has become degraded."
        --#ARGUMENTS {}
        --#SEVERITY CRITICAL
        --#TIMEINDEX 99
        --#STATE   DEGRADED

        ::= 6028

    cpqHe3CorrMemReplaceMemModule TRAP-TYPE
        ENTERPRISE compaq
        VARIABLES  { sysName, cpqHoTrapFlags }
        DESCRIPTION
            "A correctable memory log entry indicates a memory module needs
             to be replaced.

             The errors have been corrected, but the memory module should be
             replaced.  The error information is reported in the variable
             cpqHeCorrMemErrDesc."

        --#TYPE "Corr Mem Errors Require a Replacement Memory Module."
        --#SUMMARY "Correctable memory errs require a replacement memory module."
        --#ARGUMENTS {}
        --#SEVERITY MINOR
        --#TIMEINDEX 99
        --#STATE   DEGRADED


        ::= 6029


-- Deprecated in 5.10
    cpqHe3FltTolPowerSupplyDegraded TRAP-TYPE
        ENTERPRISE compaq
        VARIABLES  { sysName, cpqHoTrapFlags, cpqHeFltTolPowerSupplyChassis,
                     cpqHeFltTolPowerSupplyBay }
        DESCRIPTION
            "The fault tolerant power supply condition has been set
            to degraded for the specified chassis and bay location."

        --#TYPE "Power Supply Degraded"
        --#SUMMARY "The Power Supply Degradeded on Chassis %d, Bay %d."
        --#ARGUMENTS {2, 3}
        --#SEVERITY CRITICAL
        --#TIMEINDEX 99
        --#STATE   DEGRADED

        ::= 6030

-- Deprecated in 5.10
    cpqHe3FltTolPowerSupplyFailed TRAP-TYPE
        ENTERPRISE compaq
        VARIABLES  { sysName, cpqHoTrapFlags, cpqHeFltTolPowerSupplyChassis,
                     cpqHeFltTolPowerSupplyBay }
        DESCRIPTION
            "The fault tolerant power supply condition has been set
            to failed for the specified chassis and bay location."

        --#TYPE "Power Supply Failed"
        --#SUMMARY "The Power Supply Failed on Chassis %d, Bay %d."
        --#ARGUMENTS {2, 3}
        --#SEVERITY CRITICAL
        --#TIMEINDEX 99
        --#STATE   NONOPERATIONAL

        ::= 6031

    cpqHe3FltTolPowerRedundancyLost TRAP-TYPE
        ENTERPRISE compaq
        VARIABLES  { sysName, cpqHoTrapFlags, cpqHeFltTolPowerSupplyChassis }
        DESCRIPTION
            "The Fault Tolerant Power Supplies have lost redundancy for
            the specified chassis."

        --#TYPE "Power Redundancy Lost"
        --#SUMMARY "The Power Supplies are no longer redundant on Chassis %d."
        --#ARGUMENTS {2}
        --#SEVERITY CRITICAL
        --#TIMEINDEX 99
        --#STATE   DEGRADED

        ::= 6032

    cpqHe3FltTolPowerSupplyInserted TRAP-TYPE
        ENTERPRISE compaq
        VARIABLES  { sysName, cpqHoTrapFlags, cpqHeFltTolPowerSupplyChassis,
                     cpqHeFltTolPowerSupplyBay }
        DESCRIPTION
            "A Fault Tolerant Power Supply has been inserted into the
            specified chassis and bay location."

        --#TYPE "Power Supply Inserted"
        --#SUMMARY "The Power Supply Inserted on Chassis %d, Bay %d."
        --#ARGUMENTS {2, 3}
        --#SEVERITY CRITICAL
        --#TIMEINDEX 99
        --#STATE   OPERATIONAL

        ::= 6033

    cpqHe3FltTolPowerSupplyRemoved TRAP-TYPE
        ENTERPRISE compaq
        VARIABLES  { sysName, cpqHoTrapFlags, cpqHeFltTolPowerSupplyChassis,
                     cpqHeFltTolPowerSupplyBay }
        DESCRIPTION
            "A Fault Tolerant Power Supply has been removed from the
            specified chassis and bay location."

        --#TYPE "Power Supply Removed"
        --#SUMMARY "The Power Supply Removed on Chassis %d, Bay %d."
        --#ARGUMENTS {2, 3}
        --#SEVERITY CRITICAL
        --#TIMEINDEX 99
        --#STATE   DEGRADED

        ::= 6034

    cpqHe3FltTolFanDegraded TRAP-TYPE
        ENTERPRISE compaq
        VARIABLES  { sysName, cpqHoTrapFlags, cpqHeFltTolFanChassis,
                     cpqHeFltTolFanIndex }
        DESCRIPTION
            "The Fault Tolerant Fan condition has been set to degraded
            for the specified chassis and fan."

        --#TYPE "Fan Degraded"
        --#SUMMARY "The Fan Degraded on Chassis %d, Fan %d."
        --#ARGUMENTS {2, 3}
        --#SEVERITY CRITICAL
        --#TIMEINDEX 99
        --#STATE   DEGRADED

        ::= 6035

    cpqHe3FltTolFanFailed TRAP-TYPE
        ENTERPRISE compaq
        VARIABLES  { sysName, cpqHoTrapFlags, cpqHeFltTolFanChassis,
                     cpqHeFltTolFanIndex }
        DESCRIPTION
            "The Fault Tolerant Fan condition has been set to failed
            for the specified chassis and fan."

        --#TYPE "Fan Failed"
        --#SUMMARY "The Fan Failed on Chassis %d, Fan %d."
        --#ARGUMENTS {2, 3}
        --#SEVERITY CRITICAL
        --#TIMEINDEX 99
        --#STATE   NONOPERATIONAL

        ::= 6036

    cpqHe3FltTolFanRedundancyLost TRAP-TYPE
        ENTERPRISE compaq
        VARIABLES  { sysName, cpqHoTrapFlags, cpqHeFltTolFanChassis }
        DESCRIPTION
            "The Fault Tolerant Fans have lost redundancy for the
            specified chassis."

        --#TYPE "Fan Redundancy Lost"
        --#SUMMARY "The Fans are no longer redundant on Chassis %d."
        --#ARGUMENTS {2}
        --#SEVERITY CRITICAL
        --#TIMEINDEX 99
        --#STATE   DEGRADED

        ::= 6037

    cpqHe3FltTolFanInserted TRAP-TYPE
        ENTERPRISE compaq
        VARIABLES  { sysName, cpqHoTrapFlags, cpqHeFltTolFanChassis,
                     cpqHeFltTolFanIndex }
        DESCRIPTION
            "A Fault Tolerant Fan has been inserted into the specified
            chassis and fan location."

        --#TYPE "Fan Inserted"
        --#SUMMARY "The Fan Inserted on Chassis %d, Fan %d."
        --#ARGUMENTS {2, 3}
        --#SEVERITY CRITICAL
        --#TIMEINDEX 99
        --#STATE   OPERATIONAL

        ::= 6038

    cpqHe3FltTolFanRemoved TRAP-TYPE
        ENTERPRISE compaq
        VARIABLES  { sysName, cpqHoTrapFlags, cpqHeFltTolFanChassis,
                     cpqHeFltTolFanIndex }
        DESCRIPTION
            "A Fault Tolerant Fan has been removed from the specified
            chassis and fan location."

        --#TYPE "Fan Removed"
        --#SUMMARY "The Fan Removed on Chassis %d, Fan %d."
        --#ARGUMENTS {2, 3}
        --#SEVERITY CRITICAL
        --#TIMEINDEX 99
        --#STATE   DEGRADED

        ::= 6039

    cpqHe3TemperatureFailed TRAP-TYPE
        ENTERPRISE compaq
        VARIABLES  { sysName, cpqHoTrapFlags, cpqHeTemperatureChassis,
                     cpqHeTemperatureLocale }
        DESCRIPTION
            "The tempaerature status has been set to failed in the
            specified chassis and location.

            The system will be shutdown due to this condition."

        --#TYPE "Thermal Failure"
        --#SUMMARY "Temperature Exceeded on Chassis %d, Location %d."
        --#ARGUMENTS {2, 3}
        --#SEVERITY CRITICAL
        --#TIMEINDEX 99
        --#STATE  DEGRADED

        ::= 6040

    cpqHe3TemperatureDegraded TRAP-TYPE
        ENTERPRISE compaq
        VARIABLES  { sysName, cpqHoTrapFlags, cpqHeThermalDegradedAction,
                     cpqHeTemperatureChassis, cpqHeTemperatureLocale }
        DESCRIPTION
            "The tempaerature status has been set to degraded in the
            specified chassis and location.

            The server's temperature is outside of the normal operating
            range.  The server will be shutdown if the
            cpqHeThermalDegradedAction variable is set to shutdown(3)."

        --#TYPE "Thermal Status Degraded"
        --#SUMMARY "Temperature out of range on Chassis %d, Location %d. Shutdown may occur."
        --#ARGUMENTS {3, 4}
        --#SEVERITY CRITICAL
        --#TIMEINDEX 99
        --#STATE   DEGRADED

        ::= 6041

    cpqHe3TemperatureOk TRAP-TYPE
        ENTERPRISE compaq
        VARIABLES  { sysName, cpqHoTrapFlags, cpqHeTemperatureChassis,
                     cpqHeTemperatureLocale }
        DESCRIPTION
            "The tempaerature status has been set to ok in the
            specified chassis and location.

            The server's temperature has returned to the normal operating
            range."

        --#TYPE "Thermal Status OK"
        --#SUMMARY "Temperature Normal on Chassis %d, Location %d."
        --#ARGUMENTS {2, 3}
        --#SEVERITY INFORMATIONAL
        --#TIMEINDEX 99
        --#STATE OPERATIONAL

        ::= 6042

    cpqHe3PowerConverterDegraded TRAP-TYPE
        ENTERPRISE compaq
        VARIABLES  { sysName, cpqHoTrapFlags, cpqHePwrConvChassis,
                     cpqHePwrConvSlot, cpqHePwrConvSocket }
        DESCRIPTION
            "The DC-DC Power Converter condition has been set to degraded
            for the specified chassis, slot and socket."

        --#TYPE "Power Converter Degraded"
        --#SUMMARY "The Power Converter Degraded on Chassis %d, Slot %d, Socket %d."
        --#ARGUMENTS {2, 3, 4}
        --#SEVERITY CRITICAL
        --#TIMEINDEX 99
        --#STATE   DEGRADED


        ::= 6043

    cpqHe3PowerConverterFailed TRAP-TYPE
        ENTERPRISE compaq
        VARIABLES  { sysName, cpqHoTrapFlags, cpqHePwrConvChassis,
                     cpqHePwrConvSlot, cpqHePwrConvSocket }
        DESCRIPTION
            "The DC-DC Power Converter condition has been set to failed
            for the specified chassis, slot and socket."

        --#TYPE "Power Converter Failed"
        --#SUMMARY "The Power Converter Failed on Chassis %d, Slot %d, Socket %d."
        --#ARGUMENTS {2, 3, 4}
        --#SEVERITY CRITICAL
        --#TIMEINDEX 99
        --#STATE   NONOPERATIONAL

        ::= 6044

    cpqHe3PowerConverterRedundancyLost TRAP-TYPE
        ENTERPRISE compaq
        VARIABLES  { sysName, cpqHoTrapFlags, cpqHePwrConvChassis }
        DESCRIPTION
            "The DC-DC Power Converters have lost redundancy for the
            specified chassis."

        --#TYPE "Power Converter Redundancy Lost"
        --#SUMMARY "The Power Converters are no longer redundant on Chassis %d."
        --#ARGUMENTS {2}
        --#SEVERITY CRITICAL
        --#TIMEINDEX 99
        --#STATE   DEGRADED


        ::= 6045

    cpqHe3CacheAccelParityError TRAP-TYPE
        ENTERPRISE compaq
        VARIABLES  { sysName, cpqHoTrapFlags }
        DESCRIPTION
            "A cache accelerator parity error indicates a cache module
             needs to be replaced.

             The error information is reported in the variable
             cpqHeEventLogErrorDesc."

        --#TYPE "Cache Accel Parity Errors may require a module."
        --#SUMMARY "Cache Accelerator errors may require a replacement module."
        --#ARGUMENTS {}
        --#SEVERITY CRITICAL
        --#TIMEINDEX 99
        --#STATE   NONOPERATIONAL


        ::= 6046

    cpqHeResilientMemOnlineSpareEngaged TRAP-TYPE
        ENTERPRISE compaq
        VARIABLES  { sysName, cpqHoTrapFlags }
        DESCRIPTION
           "The Resilient Memory Online Spare Engaged.

           The Resilient Memory subsystem has detected a memory
           fault. The Online Spare Memory has been activated.

           User Action: Schedule server down-time to replace the faulty
           memory."

        --#TYPE "Online Spare Memory Engaged"
        --#SUMMARY "The Resilient Memory subsystem has engaged the online spare memory."
        --#ARGUMENTS {}
        --#SEVERITY MAJOR
        --#TIMEINDEX 99
        --#STATE DEGRADED

        ::= 6047

-- New for rev 5.10.
    cpqHe4FltTolPowerSupplyOk TRAP-TYPE
        ENTERPRISE compaq
        VARIABLES  { sysName, cpqHoTrapFlags, cpqHeFltTolPowerSupplyChassis,
                     cpqHeFltTolPowerSupplyBay, cpqHeFltTolPowerSupplyStatus,
                     cpqHeFltTolPowerSupplyModel, cpqHeFltTolPowerSupplySerialNumber,
                     cpqHeFltTolPowerSupplyAutoRev, cpqHeFltTolPowerSupplyFirmwareRev,
                     cpqHeFltTolPowerSupplySparePartNum, cpqSiServerSystemId }
        DESCRIPTION
            "The fault tolerant power supply condition has been set back
            to the OK state for the specified chassis and bay location."

        --#TYPE "Power Supply OK"
        --#SUMMARY "The Power Supply is OK on Chassis %d, Bay %d, Status %d, Model %s, Serial Num %s, Firmware %s."
        --#ARGUMENTS {2, 3, 4, 5, 6, 8}
        --#SEVERITY INFORMATIONAL
        --#TIMEINDEX 99
        --#STATE OPERATIONAL

        ::= 6048

-- New for rev 5.10.  Deprecated cpqHe3FltTolPowerSupplyDegraded
    cpqHe4FltTolPowerSupplyDegraded TRAP-TYPE
        ENTERPRISE compaq
        VARIABLES  { sysName, cpqHoTrapFlags, cpqHeFltTolPowerSupplyChassis,
                     cpqHeFltTolPowerSupplyBay, cpqHeFltTolPowerSupplyStatus,
                     cpqHeFltTolPowerSupplyModel, cpqHeFltTolPowerSupplySerialNumber,
                     cpqHeFltTolPowerSupplyAutoRev, cpqHeFltTolPowerSupplyFirmwareRev,
                     cpqHeFltTolPowerSupplySparePartNum, cpqSiServerSystemId }
        DESCRIPTION
            "The fault tolerant power supply condition has been set
            to degraded for the specified chassis and bay location."

        --#TYPE "Power Supply Degraded"
        --#SUMMARY "The Power Supply is Degraded on Chassis %d, Bay %d, Status %d, Model %s, Serial Num %s, Firmware %s."
        --#ARGUMENTS {2, 3, 4, 5, 6, 8}
        --#SEVERITY CRITICAL
        --#TIMEINDEX 99
        --#STATE DEGRADED

        ::= 6049

-- New for rev 5.10.  Deprecated cpqHe3FltTolPowerSupplyFailed
    cpqHe4FltTolPowerSupplyFailed TRAP-TYPE
        ENTERPRISE compaq
        VARIABLES  { sysName, cpqHoTrapFlags, cpqHeFltTolPowerSupplyChassis,
                     cpqHeFltTolPowerSupplyBay, cpqHeFltTolPowerSupplyStatus,
                     cpqHeFltTolPowerSupplyModel, cpqHeFltTolPowerSupplySerialNumber,
                     cpqHeFltTolPowerSupplyAutoRev, cpqHeFltTolPowerSupplyFirmwareRev,
                     cpqHeFltTolPowerSupplySparePartNum, cpqSiServerSystemId }
        DESCRIPTION
            "The fault tolerant power supply condition has been set
            to failed for the specified chassis and bay location."

        --#TYPE "Power Supply Failed"
        --#SUMMARY "The Power Supply is Failed on Chassis %d, Bay %d, Status %d, Model %s, Serial Num %s, Firmware %s."
        --#ARGUMENTS {2, 3, 4, 5, 6, 8}
        --#SEVERITY CRITICAL
        --#TIMEINDEX 99
        --#STATE NONOPERATIONAL

        ::= 6050

END
