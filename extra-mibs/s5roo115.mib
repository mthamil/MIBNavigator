-- SECTION 1: Top Level Definitions

S5-ROOT-MIB DEFINITIONS ::= BEGIN


-- 5000 Root MIB Release 1.1.5
-- Revision 05/07/98

-- Copyright 1998 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.

-- Imports

IMPORTS
	series5000
		FROM SYNOPTICS-ROOT-MIB;

-- Branches under "series5000"

-- branch for registration of values for objects
--   with syntax of OBJECT IDENTIFIER
  s5reg		OBJECT IDENTIFIER ::= { series5000 1 }

-- Branch for 'Enterprise' field values in traps
    s5Traps	OBJECT IDENTIFIER ::= { series5000 2 } 
    s5EthTrap	OBJECT IDENTIFIER ::= { s5Traps 1 } -- Ethernet
    s5TokTrap	OBJECT IDENTIFIER ::= { s5Traps 2 } -- Token Ring
    s5FddTrap	OBJECT IDENTIFIER ::= { s5Traps 3 } -- FDDI
    s5ChaTrap	OBJECT IDENTIFIER ::= { s5Traps 4 } -- Chassis
    s5ComTrap	OBJECT IDENTIFIER ::= { s5Traps 5 } -- Common
    s5EcellTrap	OBJECT IDENTIFIER ::= { s5Traps 6 } -- EtherCell
    atmTraps    OBJECT IDENTIFIER ::= { s5Traps 7 } -- Atm
    remoteLoginTrap    OBJECT IDENTIFIER ::= { s5Traps 8 } -- Remote Login
     
-- Major 5000 MIB branches
  s5Chassis	OBJECT IDENTIFIER ::= { series5000 3 }
  s5Agent	OBJECT IDENTIFIER ::= { series5000 4 }
  s5Com		OBJECT IDENTIFIER ::= { series5000 5 }
  s5Eth		OBJECT IDENTIFIER ::= { series5000 6 }
  s5Tok		OBJECT IDENTIFIER ::= { series5000 7 }
  s5Fddi	OBJECT IDENTIFIER ::= { series5000 8 }
  s5EnTop	OBJECT IDENTIFIER ::= { series5000 9 }
  s5TrTop	OBJECT IDENTIFIER ::= { series5000 10 }
  s5FdTop	OBJECT IDENTIFIER ::= { series5000 11 }
  s5EnMsTop	OBJECT IDENTIFIER ::= { series5000 13 }
  s5AtmTop	OBJECT IDENTIFIER ::= { series5000 14 }
  s5IfExt	OBJECT IDENTIFIER ::= { series5000 15 }
END
