ORALISTENER-MIB DEFINITIONS ::= BEGIN


IMPORTS
	TRAP-TYPE
		FROM RFC-1215
	DisplayString
		FROM RFC1213-MIB
	OBJECT-TYPE
		FROM RFC-1212
	Counter, Gauge, enterprises
		FROM RFC1155-SMI;

oracle OBJECT IDENTIFIER ::= { enterprises 111 }

oraListenerMIB OBJECT IDENTIFIER ::= {oracle 5 }

oraListenerObjects OBJECT IDENTIFIER ::= { oraListenerMIB  1 }

oraListenerTable OBJECT-TYPE
    SYNTAX  SEQUENCE OF OraListenerEntry
    ACCESS  not-accessible
    STATUS  mandatory
    DESCRIPTION
           "The table of information about the generic network listeners 
	   installed on a system."
    ::= { oraListenerObjects  1 }

oraListenerEntry OBJECT-TYPE
    SYNTAX  OraListenerEntry
    ACCESS  not-accessible
    STATUS  mandatory
    DESCRIPTION
           "An entry for a single generic network listener on the host."
    INDEX   { oraListenerIndex }
    ::= { oraListenerTable  1 }

OraListenerEntry ::=
    SEQUENCE {
        oraListenerIndex
            INTEGER,

        oraListenerName
            DisplayString,

        oraListenerVersion
            DisplayString,

        oraListenerStartDate
            DisplayString,

        oraListenerUptime
            TimeTicks,

        oraListenerTraceLevel
            INTEGER,

        oraListenerSecurityLevel
            INTEGER,

        oraListenerParameterFile
            DisplayString,

        oraListenerLogFile
            DisplayString,

        oraListenerTraceFile
            DisplayString,

        oraListenerState
            INTEGER,

        oraListenerNumberOfServices
            INTEGER,

        oraListenerContact
            DisplayString
    }

oraListenerIndex OBJECT-TYPE
    SYNTAX  INTEGER
    ACCESS  read-only
    STATUS  mandatory
    DESCRIPTION
           "A numeric index, unique among all the generic listeners
	   on this host."
    ::= { oraListenerEntry  1 }

oraListenerName OBJECT-TYPE
    SYNTAX  DisplayString
    ACCESS  read-only
    STATUS  mandatory
    DESCRIPTION
           "The name of this generic listener."
    ::= { oraListenerEntry  2 }

oraListenerVersion OBJECT-TYPE
    SYNTAX  DisplayString
    ACCESS  read-only
    STATUS  mandatory
    DESCRIPTION
           "The version number of this generic listener, in vendor specific
	   format."
    ::= { oraListenerEntry  3 }

oraListenerStartDate OBJECT-TYPE
    SYNTAX  DisplayString
    ACCESS  read-only
    STATUS  mandatory
    DESCRIPTION
           "The date and time at which ths generic listener was started."
    ::= { oraListenerEntry  4 }

oraListenerUptime OBJECT-TYPE
    SYNTAX  TimeTicks
    ACCESS  read-only
    STATUS  mandatory
    DESCRIPTION
           "The value of sysUpTime at the time the generic listener
	   was last started."
    ::= { oraListenerEntry  5 }

oraListenerTraceLevel OBJECT-TYPE
    SYNTAX  INTEGER {
    level1(1),
    level2(2),
    level3(3),
    user(4),
    level5(5),
    admin(6),
    level7(7),
    level8(8),
    level9(9),
    level10(10),
    level11(11),
    level12(12),
    level13(13),
    level14(14),
    level15(15),
    level16(16),
    off(17)
}
    ACCESS  read-only
    STATUS  mandatory
    DESCRIPTION
           "indicates the level of detail the trace facility the generic
	   listener records for events.  The greater the level is, the more
	   detailed the level of tracing is."
    ::= { oraListenerEntry  6 }

oraListenerSecurityLevel OBJECT-TYPE
    SYNTAX  INTEGER {
    on(1),
    off(2)
}
    ACCESS  read-only
    STATUS  mandatory
    DESCRIPTION
           "indicates whether the generic listener is password-protected
	   or not.  If security is 'on', password is required to perform
	   certain DBA tasks asgainst the listener using the listener
	   control utility.  If security is 'off', password is not required."
    ::= { oraListenerEntry  7 }

oraListenerParameterFile OBJECT-TYPE
    SYNTAX  DisplayString
    ACCESS  read-only
    STATUS  mandatory
    DESCRIPTION
           "indicates the name of the file to which configuration
	   information is stored.  Default is $ORACLE_HOME/network/admin/
	   <listener_name>.ora."
    ::= { oraListenerEntry  8 }

oraListenerLogFile OBJECT-TYPE
    SYNTAX  DisplayString
    ACCESS  read-only
    STATUS  mandatory
    DESCRIPTION
           "indicates the directory in which to find the log file that is
	   automatically generated for listener events.  Default is 
	   operating system specific; on UNIX, for example, it is
	   $ORACLE_HOME/network/log."
    ::= { oraListenerEntry  9 }

oraListenerTraceFile OBJECT-TYPE
    SYNTAX  DisplayString
    ACCESS  read-only
    STATUS  mandatory
    DESCRIPTION
           "indicates the name of the file to which trace information is
	   written.  Default is $ORACLE_HOME/network/trace/<listener_name>.trc."
    ::= { oraListenerEntry  10 }

oraListenerState OBJECT-TYPE
    SYNTAX  INTEGER {
    up(1),
    down(2)
}
    ACCESS  read-only
    STATUS  mandatory
    DESCRIPTION
           "indicates the current state of the generic listener.  'down'
	   indicates that the generic listener is not available for any
	   use, but is know to the agent.  'up' indicates that the generic
	   listener is running and available for generic use.  This would
	   be inspected by an agent on receipt of an oraListenerState trap."
    ::= { oraListenerEntry  11 }

oraListenerNumberOfServices OBJECT-TYPE
    SYNTAX  INTEGER
    ACCESS  read-only
    STATUS  mandatory
    DESCRIPTION
           "indicates the number of different types services: dedicated
	   sever, dispatcher, or prespawned shadow, configured with the
	   generic listener."
    ::= { oraListenerEntry  12 }

oraListenerContact OBJECT-TYPE
    SYNTAX  DisplayString
    ACCESS  read-write
    STATUS  mandatory
    DESCRIPTION
           "The textual identification of the contact person for this
           managed listener, together with information on how to contact
           this person."
    ::= { oraListenerEntry  13 }

oraSIDTable OBJECT-TYPE
    SYNTAX  SEQUENCE OF OraSIDEntry
    ACCESS  not-accessible
    STATUS  mandatory
    DESCRIPTION
           "The table of information about the SIDs of the databases
            for whom the listener listens on.  The system identifier
	    (SID) specifies the ORACLE System ID of the database server. "
    ::= { oraListenerObjects  5 }

oraSIDEntry OBJECT-TYPE
    SYNTAX  OraSIDEntry
    ACCESS  not-accessible
    STATUS  mandatory
    DESCRIPTION
           "An entry relating a SID to a generic listener."
    INDEX   { oraSIDName }
    ::= { oraSIDTable  1 }

OraSIDEntry ::=
    SEQUENCE {
        oraSIDListenerIndex
            INTEGER,

        oraSIDName
            DisplayString,

        oraSIDCurrentConnectedClients
            Gauge,

        oraSIDReservedConnections
            Counter
    }

oraSIDListenerIndex OBJECT-TYPE
    SYNTAX  INTEGER
    ACCESS  read-only
    STATUS  mandatory
    DESCRIPTION
           "A numeric index, unique among all the generic listeners."
    ::= { oraSIDEntry  1 }

oraSIDName OBJECT-TYPE
    SYNTAX  DisplayString
    ACCESS  read-only
    STATUS  mandatory
    DESCRIPTION
           "The name of the SID.  There is a one-to-one correspondence
            between database and SID."
    ::= { oraSIDEntry  2 }

oraSIDCurrentConnectedClients OBJECT-TYPE
    SYNTAX  Gauge
    ACCESS  read-only
    STATUS  mandatory
    DESCRIPTION
           "indicates the total number of currently connected clients
            thru this SID."
    ::= { oraSIDEntry  3 }

oraSIDReservedConnections OBJECT-TYPE
    SYNTAX  Counter
    ACCESS  read-only
    STATUS  mandatory
    DESCRIPTION
           "indicates the total number of reserved connections for
            clients on this SID."
    ::= { oraSIDEntry  4 }

oraDedicatedSrvTable OBJECT-TYPE
    SYNTAX  SEQUENCE OF OraDedicatedSrvEntry
    ACCESS  not-accessible
    STATUS  mandatory
    DESCRIPTION
           "The table of the dedicated servers associated with an system
	   identifier (SID) of the database."
    ::= { oraListenerObjects  2 }

oraDedicatedSrvEntry OBJECT-TYPE
    SYNTAX  OraDedicatedSrvEntry
    ACCESS  not-accessible
    STATUS  mandatory
    DESCRIPTION
           "An entry relating a dedicated server to a SID.
           The table is indexed first by oraSIDName, and then
           oraDedicatedSrvIndex so that all dedicated servers
           associated with a given SID can be found by SNMP
           traversal operations (get-next and get-bulk)."
    INDEX   { oraSIDName,  oraDedicatedSrvIndex }
    ::= { oraDedicatedSrvTable  1 }

OraDedicatedSrvEntry ::=
    SEQUENCE {
        oraDedicatedSrvIndex
            INTEGER,

        oraDedicatedSrvEstablishedConnections
            Counter,

        oraDedicatedSrvRejectedConnections
            Counter
    }

oraDedicatedSrvIndex OBJECT-TYPE
    SYNTAX  INTEGER
    ACCESS  read-only
    STATUS  mandatory
    DESCRIPTION
           "A numeric index, unique among all the dedicated servers."
    ::= { oraDedicatedSrvEntry  1 }

oraDedicatedSrvEstablishedConnections OBJECT-TYPE
    SYNTAX  Counter
    ACCESS  read-only
    STATUS  mandatory
    DESCRIPTION
           "indicates how many incoming connection requests have been
	   accepted by the dedicated server."
    ::= { oraDedicatedSrvEntry  2 }

oraDedicatedSrvRejectedConnections OBJECT-TYPE
    SYNTAX  Counter
    ACCESS  read-only
    STATUS  mandatory
    DESCRIPTION
           "indicates how many incoming connection requests have been
	   rejected by the dedicated server."
    ::= { oraDedicatedSrvEntry  3 }

oraDispatcherTable OBJECT-TYPE
    SYNTAX  SEQUENCE OF OraDispatcherEntry
    ACCESS  not-accessible
    STATUS  mandatory
    DESCRIPTION
           "The table of the dispatchers associated with an system
	   identifier (SID) of the database."
    ::= { oraListenerObjects  3 }

oraDispatcherEntry OBJECT-TYPE
    SYNTAX  OraDispatcherEntry
    ACCESS  not-accessible
    STATUS  mandatory
    DESCRIPTION
           "An entry relating a dispatcher to a SID.  The
            table is indexed first by oraSIDName, and then
            oraDispatcherIndex so that all dispatchers associated
            with a given SID can be found by SNMP traversal
            operations (get-next and get-bulk)."
    INDEX   { oraSIDName,  oraDispatcherIndex }
    ::= { oraDispatcherTable  1 }

OraDispatcherEntry ::=
    SEQUENCE {
        oraDispatcherIndex
            INTEGER,

        oraDispatcherEstablishedConnections
            Counter,

        oraDispatcherRejectedConnections
            Counter,

        oraDispatcherCurrentConnections
            Gauge,

        oraDispatcherMaximumConnections
            INTEGER,

        oraDispatcherState
            INTEGER,

        oraDispatcherProtocolInfo
            DisplayString
    }

oraDispatcherIndex OBJECT-TYPE
    SYNTAX  INTEGER
    ACCESS  read-only
    STATUS  mandatory
    DESCRIPTION
           "A numeric index, unique among all the dispatchers."
    ::= { oraDispatcherEntry  1 }

oraDispatcherEstablishedConnections OBJECT-TYPE
    SYNTAX  Counter
    ACCESS  read-only
    STATUS  mandatory
    DESCRIPTION
           "indicates how many incoming connection requests have been 
	   accepted by the dispatcher."
    ::= { oraDispatcherEntry  2 }

oraDispatcherRejectedConnections OBJECT-TYPE
    SYNTAX  Counter
    ACCESS  read-only
    STATUS  mandatory
    DESCRIPTION
           "indicates how many incoming connection requests have been 
	   rejected by the dispatcher."
    ::= { oraDispatcherEntry  3 }

oraDispatcherCurrentConnections OBJECT-TYPE
    SYNTAX  Gauge
    ACCESS  read-only
    STATUS  mandatory
    DESCRIPTION
           "indicates the number of connection requests currently being
	   redirected to the dispatcher."
    ::= { oraDispatcherEntry  4 }

oraDispatcherMaximumConnections OBJECT-TYPE
    SYNTAX  INTEGER
    ACCESS  read-only
    STATUS  mandatory
    DESCRIPTION
           "indicates the greatest number of connection requests that
	   will ever be accepted by the dispatcher."
    ::= { oraDispatcherEntry  5 }

oraDispatcherState OBJECT-TYPE
    SYNTAX  INTEGER {
    blocked(1),
    ready(2)
}
    ACCESS  read-only
    STATUS  mandatory
    DESCRIPTION
           "indicates the current state of the dispatcher.  'blocked'
	   indicates that the dispatcher is temporarily not accepting
	   redirected connectioin requests.  'ready' indicates that 
	   the dispacher is ready to accept any redirected conenction
	   requests."
    ::= { oraDispatcherEntry  6 }

oraDispatcherProtocolInfo OBJECT-TYPE
    SYNTAX  DisplayString
    ACCESS  read-only
    STATUS  mandatory
    DESCRIPTION
           "indicates the protocol of the dispatcher listens on as well
	   as protocol specific information.  The exact format will be
	   vendor and host specific."
    ::= { oraDispatcherEntry  7 }

oraPrespawnedSrvTable OBJECT-TYPE
    SYNTAX  SEQUENCE OF OraPrespawnedSrvEntry
    ACCESS  not-accessible
    STATUS  mandatory
    DESCRIPTION
           "The table of the prespawned servers associated with a SID."
    ::= { oraListenerObjects  4 }

oraPrespawnedSrvEntry OBJECT-TYPE
    SYNTAX  OraPrespawnedSrvEntry
    ACCESS  not-accessible
    STATUS  mandatory
    DESCRIPTION
           "An entry relating a prespawned server to a SID.
           The table is indexed first by oraSIDName, and then
           oraPrespawnedSrvIndex so that all prespawned servers
           associated with a given SID can be found by SNMP
           traversal operations (get-next and get-bulk)."
    INDEX   { oraSIDName,  oraPrespawnedSrvIndex }
    ::= { oraPrespawnedSrvTable  1 }

OraPrespawnedSrvEntry ::=
    SEQUENCE {
        oraPrespawnedSrvIndex
            INTEGER,

        oraPrespawnedSrvEstablishedConnections
            Counter,

        oraPrespawnedSrvRejectedConnections
            Counter,

        oraPrespawnedSrvCurrentConnections
            Gauge,

        oraPrespawnedSrvMaximumConnections
            INTEGER,

        oraPrespawnedSrvState
            INTEGER,

        oraPrespawnedSrvProtocolInfo
            DisplayString,

        oraPrespawnedSrvProcessorID
            DisplayString
    }

oraPrespawnedSrvIndex OBJECT-TYPE
    SYNTAX  INTEGER
    ACCESS  read-only
    STATUS  mandatory
    DESCRIPTION
           "A numeric index, unique among all the prespawned servers."
    ::= { oraPrespawnedSrvEntry  1 }

oraPrespawnedSrvEstablishedConnections OBJECT-TYPE
    SYNTAX  Counter
    ACCESS  read-only
    STATUS  mandatory
    DESCRIPTION
           "indicates how many incoming connection requests have been 
	   accepted by the prespawned server."
    ::= { oraPrespawnedSrvEntry  2 }

oraPrespawnedSrvRejectedConnections OBJECT-TYPE
    SYNTAX  Counter
    ACCESS  read-only
    STATUS  mandatory
    DESCRIPTION
           "indicates how many incoming connection requests have been 
	   rejected by the prespawned server."
    ::= { oraPrespawnedSrvEntry  3 }

oraPrespawnedSrvCurrentConnections OBJECT-TYPE
    SYNTAX  Gauge
    ACCESS  read-only
    STATUS  mandatory
    DESCRIPTION
           "indicates the number of connection requests currently being
	   redirected to the prespawned server."
    ::= { oraPrespawnedSrvEntry  4 }

oraPrespawnedSrvMaximumConnections OBJECT-TYPE
    SYNTAX  INTEGER
    ACCESS  read-only
    STATUS  mandatory
    DESCRIPTION
           "indicates the greatest number of connection requests that
	   will ever be accepted by the prespawned server."
    ::= { oraPrespawnedSrvEntry  5 }

oraPrespawnedSrvState OBJECT-TYPE
    SYNTAX  INTEGER {
    blocked(1),
    ready(2)
}
    ACCESS  read-only
    STATUS  mandatory
    DESCRIPTION
           "indicates the current state of the prespawned server.  'blocked'
	   indicates that the prespawned server is temporarily not
	   accepting redirected connection requests.  'ready' indicates
	   the prespawned server is ready to accept any redirected conenction
	   requests."
    ::= { oraPrespawnedSrvEntry  6 }

oraPrespawnedSrvProtocolInfo OBJECT-TYPE
    SYNTAX  DisplayString
    ACCESS  read-only
    STATUS  mandatory
    DESCRIPTION
           "indicates the protocol of the prespawned server listens on as well
	   as protocol specific information.  The exact format will be
	   vendor and host specific."
    ::= { oraPrespawnedSrvEntry  7 }

oraPrespawnedSrvProcessorID OBJECT-TYPE
    SYNTAX  DisplayString
    ACCESS  read-only
    STATUS  mandatory
    DESCRIPTION
           "indicates the process ID of the prespawned server."
    ::= { oraPrespawnedSrvEntry  8 }

oraListenAddressTable OBJECT-TYPE
    SYNTAX  SEQUENCE OF OraListenAddressEntry
    ACCESS  not-accessible
    STATUS  mandatory
    DESCRIPTION
           "The table of information about the addresses that the listener
            is listening at."
    ::= { oraListenerObjects  6 }

oraListenAddressEntry OBJECT-TYPE
    SYNTAX  OraListenAddressEntry
    ACCESS  not-accessible
    STATUS  mandatory
    DESCRIPTION
           "An entry relating the listen addresses to a generic listener."
    INDEX   { oraListenerIndex,  oraListenAddressIndex }
    ::= { oraListenAddressTable  1 }

OraListenAddressEntry ::=
    SEQUENCE {
        oraListenAddressIndex
            INTEGER,

        oraListenAddress
            DisplayString
    }

oraListenAddressIndex OBJECT-TYPE
    SYNTAX  INTEGER
    ACCESS  read-only
    STATUS  mandatory
    DESCRIPTION
           "A numeric index, unique among all the listen addresses."
    ::= { oraListenAddressEntry  1 }

oraListenAddress OBJECT-TYPE
    SYNTAX  DisplayString
    ACCESS  read-only
    STATUS  mandatory
    DESCRIPTION
           "The addresses to whom the listener is listening at."
    ::= { oraListenAddressEntry  2 }

oraListenerTraps OBJECT IDENTIFIER ::= { oraListenerMIB  2 }

oraListenerStateChange TRAP-TYPE
    ENTERPRISE  oraListenerTraps
    VARIABLES   { oraListenerState }
    DESCRIPTION
           "An rdbmsStateChange trap signifies that one of the generic
           listeners managed by this agent has changed its oraListenerState
           in a way that makes it less accessible for use."
    ::= 1

END
