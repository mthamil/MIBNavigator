-- MIB created 11/10/97 15:20:43, by
--   SMIC (the next generation) version 1.6.29, November 22, 1994.

IPOA-MIB DEFINITIONS ::= BEGIN

-- From file: "ipoa.mi2"
-- Compile options "G A T M"

IMPORTS
    experimental, Integer32, IpAddress, Counter32
            FROM SNMPv2-SMI-v1
    OBJECT-TYPE
            FROM RFC-1212
    RowStatus
            FROM SNMPv2-TC-v1
    AtmConnKind
            FROM ATM-TC-MIB
    ipNetToMediaNetAddress, ipNetToMediaIfIndex, 
    ipNetToMediaPhysAddress, ipAdEntAddr
            FROM RFC1213-MIB
    InterfaceIndex
            FROM IF-MIB;

ipoaMIB OBJECT IDENTIFIER ::= { experimental 78 }
-- MODULE-IDENTITY
--  LastUpdated
--    9705130000Z
--  OrgName
--    IETF Internetworking Over NBMA Working Group (ion)
--  ContactInfo
--    Maria Greene (greene@ultranet.com)
--     Independent Contractor
--    
--     Jim Luciani (jluciani@BayNetworks.com)
--     Bay Networks
--    
--     Kenneth White (kennethw@vnet.ibm.com)
--     Ted Kuo (tkuo@eos.ncsu.edu)
--     IBM Corp.
--  Descr
--    This module defines a portion of the management
--    information base (MIB) for managing Classical IP and ARP
--    over ATM entities.

ipoaObjects     OBJECT IDENTIFIER ::= { ipoaMIB 1 }
ipoaNotifications OBJECT IDENTIFIER ::= { ipoaMIB 2 }
ipoaConformance OBJECT IDENTIFIER ::= { ipoaMIB 3 }
ipoaGroups      OBJECT IDENTIFIER ::= { ipoaConformance 1 }
ipoaCompliances OBJECT IDENTIFIER ::= { ipoaConformance 2 }

InterfaceIndexOrZero ::= Integer32(0..65535)

IpoaEncapsType ::= INTEGER {
        llcSnap(1),
        vcMuxed(2),
        other(3)
        }
-- TEXTUAL-CONVENTION
--  Status
--    mandatory
--  Descr
--    The encapsulation type used on a VC.

IpoaVpiInteger ::= Integer32(0..255)
-- TEXTUAL-CONVENTION
--  Status
--    mandatory
--  Descr
--    An integer large enough to hold a VPI.

IpoaVciInteger ::= Integer32(0..65535)
-- TEXTUAL-CONVENTION
--  Status
--    mandatory
--  Descr
--    An integer large enough to hold a VCI.

IpoaAtmAddr ::= OCTET STRING(SIZE(0..40))
-- TEXTUAL-CONVENTION
--  DspHint
--    1x
--  Status
--    mandatory
--  Descr
--    The ATM address used by the network entity.
--     The address type can be determined by the
--     OCTET STRING size. IpoaAtmAddr can be comprised
--     of both an ATM Address and a subaddress. The
--     ATM Address portion is required and must be
--     first in the OCTET STRING.
--    
--     An implementation must use BCD encoding to
--     represent a E.164 address as a MIB object.

ipoaLisTrapEnable OBJECT-TYPE
    SYNTAX INTEGER {
        enabled(1),
        disabled(2)
        }
    ACCESS read-write
    STATUS mandatory
    DESCRIPTION
        "Indicates whether ipoaLisCreate and ipoaLisDelete
         traps should be generated by this system.
        
         By default, this object should have the value
         enabled(1) for systems where ATMARP servers are
         present and disabled(2) on systems where only
         clients reside."
    ::= { ipoaObjects 1 }

ipoaLisTable OBJECT-TYPE
    SYNTAX SEQUENCE OF IpoaLisEntry
    ACCESS not-accessible
    STATUS mandatory
    DESCRIPTION
        "There is one entry in this table for every Logical IP Subnet
        (LIS) that this system is a member of."
    ::= { ipoaObjects 2 }

ipoaLisEntry OBJECT-TYPE
    SYNTAX IpoaLisEntry
    ACCESS not-accessible
    STATUS mandatory
    DESCRIPTION
        "Information about a single LIS that this system is a member
        of.
        
        This table is indexed by an IP subnet address.
        
        Membership in a LIS is independent of the actual ATM
        physical interfaces being used. The ipoaLisTable defines
        all LISes that a system is a member of. The ipAddrTable
        and the ipoaClientTable provides the mapping from local
        IP address to ATM physical interface. The
        ipoaLisIfMappingTable provides the mappings between
        Logical IP Subnets and interfaces.
        
        The ipoaLisTable is indexed by ipoaLisSubnetAddr.
        An entry in the ipAddrTable should exist for each
        ipAddrEntry that is associated with an IP over ATM
        interface. Its ipAdEntAddr and ipAdEntNetMask when ANDed
        should map to a ipoaLisSubnetAddr."
    INDEX { ipoaLisSubnetAddr }
    ::= { ipoaLisTable 1 }

IpoaLisEntry ::= SEQUENCE {
    ipoaLisSubnetAddr IpAddress,
    ipoaLisDefaultMtu Integer32,
    ipoaLisDefaultEncapsType IpoaEncapsType,
    ipoaLisInactivityTimer Integer32,
    ipoaLisMinHoldingTime Integer32,
    ipoaLisQDepth Integer32,
    ipoaLisMaxCalls Integer32,
    ipoaLisCacheEntryAge Integer32,
    ipoaLisRetries Integer32,
    ipoaLisTimeout Integer32,
    ipoaLisDefaultPeakCellRate Integer32,
    ipoaLisActiveVcs Counter32,
    ipoaLisRowStatus RowStatus
    }

ipoaLisSubnetAddr OBJECT-TYPE
    SYNTAX IpAddress
    ACCESS read-only
    STATUS mandatory
    DESCRIPTION
        "The IP subnet address associated with this LIS."
    ::= { ipoaLisEntry 1 }

ipoaLisDefaultMtu OBJECT-TYPE
    SYNTAX Integer32(0..65535)
    ACCESS read-write
    STATUS mandatory
    DESCRIPTION
        "The default MTU used within this LIS. Note that the actual
        size used for a VC between two members of the LIS may be
        negotiated during connection setup and may be different than
        this value. The ipoaVcNegotiatedMtu object indicates the
        actual MTU in use for a particular VC."
    DEFVAL { 9180 }
    ::= { ipoaLisEntry 2 }

ipoaLisDefaultEncapsType OBJECT-TYPE
    SYNTAX IpoaEncapsType
--    Rsyntax INTEGER {
--        llcSnap(1),
--        vcMuxed(2),
--        other(3)
--        }
    ACCESS read-write
    STATUS mandatory
    DESCRIPTION
        "The default encapsulation to use on VCs created for this
        LIS. Note that the actual encapsulation type may be negotiated
        during connection setup and may be different than this
        value. The ipoaVcNegotiatedEncapsType object indicates the
        actual encapsulation in use for a particular VC."
    DEFVAL { llcSnap }
    ::= { ipoaLisEntry 3 }

ipoaLisInactivityTimer OBJECT-TYPE
    SYNTAX Integer32
--  Units
--    seconds
    ACCESS read-write
    STATUS mandatory
    DESCRIPTION
        "The time, in seconds, before a call established for an
        ipNetToMediaEntry on a client will timeout due to no
        traffic being passed on the VC. A value of 0 implies
        no time out."
    REFERENCE
        "RFC1755, Sec. 3.4 VC Teardown"
    DEFVAL { 300 }
    ::= { ipoaLisEntry 4 }

ipoaLisMinHoldingTime OBJECT-TYPE
    SYNTAX Integer32(0..65535)
--  Units
--    seconds
    ACCESS read-write
    STATUS mandatory
    DESCRIPTION
        "The minimum amount of time, in seconds, that a call will
         remain open. If 0 then ipoaInactivityTimer will
         completely determine when a call is terminated."
    REFERENCE
        "RFC1755, Sec. 3.4 VC Teardown"
    DEFVAL { 60 }
    ::= { ipoaLisEntry 5 }

ipoaLisQDepth OBJECT-TYPE
    SYNTAX Integer32(1..65535)
--  Units
--    packets
    ACCESS read-write
    STATUS mandatory
    DESCRIPTION
        "The maximum number of outstanding requests that are
         allowed while waiting for ATMARP replies and
         In_ATMARP replies for this LIS."
    DEFVAL { 1 }
    ::= { ipoaLisEntry 6 }

ipoaLisMaxCalls OBJECT-TYPE
    SYNTAX Integer32(1..65535)
    ACCESS read-write
    STATUS mandatory
    DESCRIPTION
        "The maximum number of SVCs that can be established
        simultaneously."
    DEFVAL { 500 }
    ::= { ipoaLisEntry 7 }

ipoaLisCacheEntryAge OBJECT-TYPE
    SYNTAX Integer32(60..1200)
--  Units
--    seconds
    ACCESS read-write
    STATUS mandatory
    DESCRIPTION
        "The time, in seconds, before an ipNetToMediaEntry will age
        out of the table. Note that the default value will be
        different for a client and a server. A ATMARP server should
        use a default of 1200 and a client should use 900."
    DEFVAL { 900 }
    ::= { ipoaLisEntry 8 }

ipoaLisRetries OBJECT-TYPE
    SYNTAX Integer32(0..10)
    ACCESS read-write
    STATUS mandatory
    DESCRIPTION
        "The number of times the ATMARP request will be retried when
        no response is received in the timeout interval indicated by
        ipoaLisTimeout."
    DEFVAL { 2 }
    ::= { ipoaLisEntry 9 }

ipoaLisTimeout OBJECT-TYPE
    SYNTAX Integer32(1..60)
--  Units
--    seconds
    ACCESS read-write
    STATUS mandatory
    DESCRIPTION
        "The time to wait, in seconds, before retransmission of an ARP
        PDU."
    DEFVAL { 10 }
    ::= { ipoaLisEntry 10 }

ipoaLisDefaultPeakCellRate OBJECT-TYPE
    SYNTAX Integer32
    ACCESS read-write
    STATUS mandatory
    DESCRIPTION
        "This object is the signalling parameter that
         should be used when setting up all best effort
         VCCs. This parameter applies to the forward and
         backward direction on a per best effort VCC basis.
         A value of zero implies that no configured default
        
        
        
        
        
         exists and that local policy should be used to
         determine the actual default to used during
         call setup. ATM Signaling Support for IP over ATM
         (RFC 1755) recommends 1/10th of the ATM interface's
         speed."
    ::= { ipoaLisEntry 11 }

ipoaLisActiveVcs OBJECT-TYPE
    SYNTAX Counter32
    ACCESS read-only
    STATUS mandatory
    DESCRIPTION
        "Number of active SVCs."
    ::= { ipoaLisEntry 12 }

ipoaLisRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted in the
        ipoaLisTable.
        
        When the ipoaLisRowStatus deleted (by setting this object to
        destroy(6)), this has the side-effect of removing all
        entries from the ipNetToMediaTable that are associated with
        this LIS (in other words, it flushes the entity's ATMARP
        cache). It also removes the ipoaVcTable entries that were
        associated with those ipNetToMediaTable entries. Destroying
        the row also removes the corresponding entries in the
        ipoaArpSrvrTable, ipoaArpClientTable,
        ipoaLisIfMappingTable and ipoaArpRemoteSrvrTable.
        
        Entries in both the ipNetToMediaTable and the ipoaVcTable
        that are associated with a ipoaConfigPvcEntry are not
        effected by changes to ipoaLisRowStatus."
    REFERENCE
        "RFC 1903, 'Textual Conventions for version 2 of the Simple
        Network Management Protocol (SNMPv2).'"
    ::= { ipoaLisEntry 13 }

ipoaLisIfMappingTable OBJECT-TYPE
    SYNTAX SEQUENCE OF IpoaLisIfMappingEntry
    ACCESS not-accessible
    STATUS mandatory
    DESCRIPTION
        "There is one entry in this table for every combination
         of ipoaLisEntry and IP over ATM interface."
    ::= { ipoaObjects 3 }

ipoaLisIfMappingEntry OBJECT-TYPE
    SYNTAX IpoaLisIfMappingEntry
    ACCESS not-accessible
    STATUS mandatory
    DESCRIPTION
        "Defines an entry in the ipoaLisIfMappingTable."
    INDEX { ipoaLisSubnetAddr, ipoaLisIfMappingIfIndex }
    ::= { ipoaLisIfMappingTable 1 }

IpoaLisIfMappingEntry ::= SEQUENCE {
    ipoaLisIfMappingIfIndex InterfaceIndex,
    ipoaLisIfMappingStatus RowStatus
    }

ipoaLisIfMappingIfIndex OBJECT-TYPE
    SYNTAX InterfaceIndex
--    Rsyntax Integer32
    ACCESS not-accessible
    STATUS mandatory
    DESCRIPTION
        "The ipAdEntIfIndex object from a ipAddrEntry
         is used as an index to this table when its
         ipAdEntAddr is in the subnet implied by
         ipoaLisSubnetAddr."
    ::= { ipoaLisIfMappingEntry 1 }

ipoaLisIfMappingStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted in the
        ipoaLisIfMappingTable."
    REFERENCE
        "RFC 1903, 'Textual Conventions for version 2 of the Simple
        Network Management Protocol (SNMPv2).'"
    ::= { ipoaLisIfMappingEntry 2 }

ipoaArpClientTable OBJECT-TYPE
    SYNTAX SEQUENCE OF IpoaArpClientEntry
    ACCESS not-accessible
    STATUS mandatory
    DESCRIPTION
        "The ATMARP clients running on this system."
    ::= { ipoaObjects 4 }

ipoaArpClientEntry OBJECT-TYPE
    SYNTAX IpoaArpClientEntry
    ACCESS not-accessible
    STATUS mandatory
    DESCRIPTION
        "Information about a single ATMARP Client. Clients can be
        started and stopped by adding and removing entries from this
        table. Note that adding and removing entries from this table
        may have the same effect on the corresponding ipAddrTable
        entry. An entry in the ipoaArpClientTable has a corresponding
        entry in the ipAddrTable. Both are indexed by ipAdEntAddr.
        The ifIndex and subnet mask of a client entry are the
        ipAddrEntry's ipAdEntIfIndex and ipAdEntNetMask respectively.
        A remote creation of an object in this table requires
        that either the corresponding ipAddrTable entry exists or
        that ipAdEntIfIndex and ipAdEntNetMask be specified in the
        creation of a ipoaArpClientEntry at a minimum in order
        to create the corresponding ipAddrEntry. Specification
        of ipAdEntBcastAddr and ipAdEntReasmMaxSize to complete a
        ipAddrEntry is implementation dependent."
    INDEX { ipAdEntAddr }
    ::= { ipoaArpClientTable 1 }

IpoaArpClientEntry ::= SEQUENCE {
    ipoaArpClientAtmAddr IpoaAtmAddr,
    ipoaArpClientSrvrInUse IpoaAtmAddr,
    ipoaArpClientInArpReqsIn Counter32,
    ipoaArpClientInArpReqsOut Counter32,
    ipoaArpClientInArpRepliesIn Counter32,
    ipoaArpClientInArpRepliesOut Counter32,
    ipoaArpClientInArpInvalidReqsIn Counter32,
    ipoaArpClientInArpInvalidReqsOut Counter32,
    ipoaArpClientArpReqsIn Counter32,
    ipoaArpClientArpReqsOut Counter32,
    ipoaArpClientArpRepliesIn Counter32,
    ipoaArpClientArpRepliesOut Counter32,
    ipoaArpClientArpNaksIn Counter32,
    ipoaArpClientArpNaksOut Counter32,
    ipoaArpClientArpOpUnknown Counter32,
    ipoaArpClientArpSrvrNoResp Counter32,
    ipoaArpClientRowStatus RowStatus
    }

ipoaArpClientAtmAddr OBJECT-TYPE
    SYNTAX IpoaAtmAddr
--    Rsyntax OCTET STRING(SIZE(0..40))
    ACCESS read-write
    STATUS mandatory
    DESCRIPTION
        "The ATM address of the client."
    ::= { ipoaArpClientEntry 1 }

ipoaArpClientSrvrInUse OBJECT-TYPE
    SYNTAX IpoaAtmAddr
--    Rsyntax OCTET STRING(SIZE(0..40))
    ACCESS read-only
    STATUS mandatory
    DESCRIPTION
        "The ATM address of the ATMARP Server,
         ipoaArpRemoteSrvrAtmAddr,
         in use by this client. A null octet string implies that
         communication with a Remote ATMARP Server is not in effect."
    DEFVAL { ''h }
    ::= { ipoaArpClientEntry 2 }

ipoaArpClientInArpReqsIn OBJECT-TYPE
    SYNTAX Counter32
    ACCESS read-only
    STATUS mandatory
    DESCRIPTION
        "The number of InATMARP requests received by this client."
    ::= { ipoaArpClientEntry 3 }

ipoaArpClientInArpReqsOut OBJECT-TYPE
    SYNTAX Counter32
    ACCESS read-only
    STATUS mandatory
    DESCRIPTION
        "The number of InATMARP requests sent by this client."
    ::= { ipoaArpClientEntry 4 }

ipoaArpClientInArpRepliesIn OBJECT-TYPE
    SYNTAX Counter32
    ACCESS read-only
    STATUS mandatory
    DESCRIPTION
        "The number of InATMARP replies received by this client."
    ::= { ipoaArpClientEntry 5 }

ipoaArpClientInArpRepliesOut OBJECT-TYPE
    SYNTAX Counter32
    ACCESS read-only
    STATUS mandatory
    DESCRIPTION
        "Total number of InATMARP replies sent by this client."
    ::= { ipoaArpClientEntry 6 }

ipoaArpClientInArpInvalidReqsIn OBJECT-TYPE
    SYNTAX Counter32
    ACCESS read-only
    STATUS mandatory
    DESCRIPTION
        "The number of times that this client detected an invalid
         InATMARP request."
    ::= { ipoaArpClientEntry 7 }

ipoaArpClientInArpInvalidReqsOut OBJECT-TYPE
    SYNTAX Counter32
    ACCESS read-only
    STATUS mandatory
    DESCRIPTION
        "The number of times that this client did not receive
         a InATMARP reply."
    ::= { ipoaArpClientEntry 8 }

ipoaArpClientArpReqsIn OBJECT-TYPE
    SYNTAX Counter32
    ACCESS read-only
    STATUS mandatory
    DESCRIPTION
        "Total number of ATMARP requests received by this client."
    ::= { ipoaArpClientEntry 9 }

ipoaArpClientArpReqsOut OBJECT-TYPE
    SYNTAX Counter32
    ACCESS read-only
    STATUS mandatory
    DESCRIPTION
        "Total number of ATMARP requests sent by this client."
    ::= { ipoaArpClientEntry 10 }

ipoaArpClientArpRepliesIn OBJECT-TYPE
    SYNTAX Counter32
    ACCESS read-only
    STATUS mandatory
    DESCRIPTION
        "Total number of ATMARP replies received by this client."
    ::= { ipoaArpClientEntry 11 }

ipoaArpClientArpRepliesOut OBJECT-TYPE
    SYNTAX Counter32
    ACCESS read-only
    STATUS mandatory
    DESCRIPTION
        "Total number of ATMARP replies sent by this client."
    ::= { ipoaArpClientEntry 12 }

ipoaArpClientArpNaksIn OBJECT-TYPE
    SYNTAX Counter32
    ACCESS read-only
    STATUS mandatory
    DESCRIPTION
        "Total number of negative ATMARP replies
         received by this client."
    ::= { ipoaArpClientEntry 13 }

ipoaArpClientArpNaksOut OBJECT-TYPE
    SYNTAX Counter32
    ACCESS read-only
    STATUS mandatory
    DESCRIPTION
        "Total number of negative ATMARP replies
         send by this client."
    ::= { ipoaArpClientEntry 14 }

ipoaArpClientArpOpUnknown OBJECT-TYPE
    SYNTAX Counter32
    ACCESS read-only
    STATUS mandatory
    DESCRIPTION
        "The number of times that this client received
         an ATMARP message with an operation code for which it
         is not coded to support."
    ::= { ipoaArpClientEntry 15 }

ipoaArpClientArpSrvrNoResp OBJECT-TYPE
    SYNTAX Counter32
    ACCESS read-only
    STATUS mandatory
    DESCRIPTION
        "The number of times this client failed to receive
         a response from a ATMARP Server within the
         ipoaLisTimeout value for ipoaLisRetries times.
         This may imply that the client will re-elect a
         primary ATMARP server for this LIS from the
         ipoaArpRemoteSrvrTable."
    ::= { ipoaArpClientEntry 16 }

ipoaArpClientRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted from the
        ipoaArpClientTable."
    REFERENCE
        "RFC 1903, 'Textual Conventions for version 2 of the Simple
        Network Management Protocol (SNMPv2).'"
    ::= { ipoaArpClientEntry 17 }

ipoaArpSrvrTable OBJECT-TYPE
    SYNTAX SEQUENCE OF IpoaArpSrvrEntry
    ACCESS not-accessible
    STATUS mandatory
    DESCRIPTION
        "The ATMARP servers running on this system."
    ::= { ipoaObjects 5 }

ipoaArpSrvrEntry OBJECT-TYPE
    SYNTAX IpoaArpSrvrEntry
    ACCESS not-accessible
    STATUS mandatory
    DESCRIPTION
        "Information about an ATMARP server within a LIS. An entry in
        this table has two indexes: first the ipAdEntAddr, which is
        the IP address that this system uses as a member of the LIS,
        and then the ipoaArpSrvrAddr, which is the ATM address of the
        ATMARP server.
        
        Entries may be created by a management application using the
        ipoaArpSrvrRowStatus object.  Entries in
        this table may also be created by the system and not by a
        management application, for example as a result of ILMI.
        
        Entries in this table may be deleted by setting the
        ipoaArpSrvrRowStatus object to 'destroy(6)'. This includes
        entries that were added by the system and not by a management
        application."
    INDEX { ipAdEntAddr, ipoaArpSrvrAddr }
    ::= { ipoaArpSrvrTable 1 }

IpoaArpSrvrEntry ::= SEQUENCE {
    ipoaArpSrvrAddr IpoaAtmAddr,
    ipoaArpSrvrLis IpAddress,
    ipoaArpSrvrInArpReqsIn Counter32,
    ipoaArpSrvrInArpReqsOut Counter32,
    ipoaArpSrvrInArpRepliesIn Counter32,
    ipoaArpSrvrInArpRepliesOut Counter32,
    ipoaArpSrvrInArpInvalidReqsIn Counter32,
    ipoaArpSrvrInArpInvalidReqsOut Counter32,
    ipoaArpSrvrArpReqsIn Counter32,
    ipoaArpSrvrArpRepliesOut Counter32,
    ipoaArpSrvrArpNaksOut Counter32,
    ipoaArpSrvrArpDupIpAddr Counter32,
    ipoaArpSrvrArpOpUnknown Counter32,
    ipoaArpSrvrRowStatus RowStatus
    }

ipoaArpSrvrAddr OBJECT-TYPE
    SYNTAX IpoaAtmAddr
--    Rsyntax OCTET STRING(SIZE(0..40))
    ACCESS not-accessible
    STATUS mandatory
    DESCRIPTION
        "The ATM address of the ATMARP server."
    ::= { ipoaArpSrvrEntry 1 }

ipoaArpSrvrLis OBJECT-TYPE
    SYNTAX IpAddress
    ACCESS read-write
    STATUS mandatory
    DESCRIPTION
        "The subnet address that identifies the LIS this server is
        associated with."
    ::= { ipoaArpSrvrEntry 2 }

ipoaArpSrvrInArpReqsIn OBJECT-TYPE
    SYNTAX Counter32
    ACCESS read-only
    STATUS mandatory
    DESCRIPTION
        "The number of InATMARP requests received by this ATMARP
        server."
    ::= { ipoaArpSrvrEntry 3 }

ipoaArpSrvrInArpReqsOut OBJECT-TYPE
    SYNTAX Counter32
    ACCESS read-only
    STATUS mandatory
    DESCRIPTION
        "The number of InATMARP requests sent by this ATMARP server."
    ::= { ipoaArpSrvrEntry 4 }

ipoaArpSrvrInArpRepliesIn OBJECT-TYPE
    SYNTAX Counter32
    ACCESS read-only
    STATUS mandatory
    DESCRIPTION
        "The number of InATMARP replies received by this ATMARP
        
        
        
        
        
        server."
    ::= { ipoaArpSrvrEntry 5 }

ipoaArpSrvrInArpRepliesOut OBJECT-TYPE
    SYNTAX Counter32
    ACCESS read-only
    STATUS mandatory
    DESCRIPTION
        "The number of InATMARP replies sent by this ATMARP server."
    ::= { ipoaArpSrvrEntry 6 }

ipoaArpSrvrInArpInvalidReqsIn OBJECT-TYPE
    SYNTAX Counter32
    ACCESS read-only
    STATUS mandatory
    DESCRIPTION
        "The number of invalid InATMARP requests received by
         this ATMARP server."
    ::= { ipoaArpSrvrEntry 7 }

ipoaArpSrvrInArpInvalidReqsOut OBJECT-TYPE
    SYNTAX Counter32
    ACCESS read-only
    STATUS mandatory
    DESCRIPTION
        "The number of times that this server did not receive
         a InATMARP reply."
    ::= { ipoaArpSrvrEntry 8 }

ipoaArpSrvrArpReqsIn OBJECT-TYPE
    SYNTAX Counter32
    ACCESS read-only
    STATUS mandatory
    DESCRIPTION
        "Total number of ATMARP requests received by this ATMARP
        server."
    ::= { ipoaArpSrvrEntry 9 }

ipoaArpSrvrArpRepliesOut OBJECT-TYPE
    SYNTAX Counter32
    ACCESS read-only
    STATUS mandatory
    DESCRIPTION
        "Total number of ATMARP replies sent by this ATMARP server."
    ::= { ipoaArpSrvrEntry 10 }

ipoaArpSrvrArpNaksOut OBJECT-TYPE
    SYNTAX Counter32
    ACCESS read-only
    STATUS mandatory
    DESCRIPTION
        "Total number of negative ATMARP replies sent by this
         ATMARP server."
    ::= { ipoaArpSrvrEntry 11 }

ipoaArpSrvrArpDupIpAddr OBJECT-TYPE
    SYNTAX Counter32
    ACCESS read-only
    STATUS mandatory
    DESCRIPTION
        "The number of times that a duplicate IP address was
         detected by this ATMARP server."
    ::= { ipoaArpSrvrEntry 12 }

ipoaArpSrvrArpOpUnknown OBJECT-TYPE
    SYNTAX Counter32
    ACCESS read-only
    STATUS mandatory
    DESCRIPTION
        "The number of times that this ATMARP server received
         an ATMARP message with an operation code for which it
         is not coded to support."
    ::= { ipoaArpSrvrEntry 13 }

ipoaArpSrvrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted from the
        ipoaArpSrvrTable."
    REFERENCE
        "RFC 1903, 'Textual Conventions for version 2 of the Simple
        Network Management Protocol (SNMPv2).'"
    ::= { ipoaArpSrvrEntry 14 }

ipoaArpRemoteSrvrTable OBJECT-TYPE
    SYNTAX SEQUENCE OF IpoaArpRemoteSrvrEntry
    ACCESS not-accessible
    STATUS mandatory
    DESCRIPTION
        "A table of non-local ATMARP servers associated with a LIS.
        An entry in this table has three indexes: first the
        ipoaLisSubnetAddr of the LIS that the corresponding
        
        
        
        ATMARP server provides ATMARP services for, then the
        ipoaArpRemoteSrvrAtmAddr, which is the ATM address of the
        remote ATMARP server and finally the ifIndex of the
        interface on which the VC to the ATMARP Remote Server
        will be opened. A ifIndex value of 0 should be used
        when a single VC is to be shared for ATMARP purposes
        by multiple interfaces."
    ::= { ipoaObjects 6 }

ipoaArpRemoteSrvrEntry OBJECT-TYPE
    SYNTAX IpoaArpRemoteSrvrEntry
    ACCESS not-accessible
    STATUS mandatory
    DESCRIPTION
        "Information about one non-local ATMARP server."
    INDEX { ipoaLisSubnetAddr, ipoaArpRemoteSrvrAtmAddr, ipoaArpRemoteSrvrIfIndex }
    ::= { ipoaArpRemoteSrvrTable 1 }

IpoaArpRemoteSrvrEntry ::= SEQUENCE {
    ipoaArpRemoteSrvrAtmAddr IpoaAtmAddr,
    ipoaArpRemoteSrvrRowStatus RowStatus,
    ipoaArpRemoteSrvrIfIndex InterfaceIndexOrZero,
    ipoaArpRemoteSrvrIpAddr IpAddress
    }

ipoaArpRemoteSrvrAtmAddr OBJECT-TYPE
    SYNTAX IpoaAtmAddr
--    Rsyntax OCTET STRING(SIZE(0..40))
    ACCESS not-accessible
    STATUS mandatory
    DESCRIPTION
        "The ATM address of the remote ATMARP server."
    ::= { ipoaArpRemoteSrvrEntry 1 }

ipoaArpRemoteSrvrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted from the
        ipoaArpRemoteSrvrTable as well as indicating the weather a
        VC exists to the Remote ATMARP Server.
        
        ipoaArpRemoteSrvrRowStatus states:
        active(1)       - VC exists to Remote ATMARP Server who's IP
                          Address is stored in ipoaArpRemoteSrvrIpAddr.
                          This VC can be determined by searching the
                          ipoaVcTable using ipoaArpRemoteSrvrIfIndex
        
        
        
        
        
        
                          (if not 0 otherwise ignore ipNetToMediaIfIndex
                          index) and ipoaArpRemoteSrvrIpAddr. A
                          ipoaArpClientEntry should exist were its
                          ipoaArpClientSrvrInUse object has the same
                          value as ipoaArpRemoteSrvrAtmAddr.
        notInService(2)  - Entry exists without an active VC to
                          the Remote ATMARP Server.
        notReady(3)      - ipoaArpRemoteSrvrEntry is incomplete.
        createAndGo(4)   - Value used to remotely create an entry
                          and then active it.
        createAndWait(4) - Value used to remotely create an entry and
                          leave entry inactive with either
                          notInService or notReady state.
        destroy(6)       - When ipoaArpRemoteSrvrRowStatus is set with
                          this value the corresponding table entry is
                          deleted."
    REFERENCE
        "RFC 1903, 'Textual Conventions for version 2 of the Simple
        Network Management Protocol (SNMPv2).'"
    ::= { ipoaArpRemoteSrvrEntry 2 }

ipoaArpRemoteSrvrIfIndex OBJECT-TYPE
    SYNTAX InterfaceIndexOrZero
--    Rsyntax Integer32(0..65535)
    ACCESS not-accessible
    STATUS mandatory
    DESCRIPTION
        "The ifIndex of the interface that the VC to the
         Remote ATMARP Server is associated with."
    ::= { ipoaArpRemoteSrvrEntry 3 }

ipoaArpRemoteSrvrIpAddr OBJECT-TYPE
    SYNTAX IpAddress
    ACCESS read-only
    STATUS mandatory
    DESCRIPTION
        "The IP Address of the Remote ATMARP Server. A value of
         0 implies that this address isn't known."
    ::= { ipoaArpRemoteSrvrEntry 4 }

ipoaVcTable OBJECT-TYPE
    SYNTAX SEQUENCE OF IpoaVcEntry
    ACCESS not-accessible
    STATUS mandatory
    DESCRIPTION
        "A system that support IP over ATM is an IP system and
        therefore must support all of the appropriate tables from
        RFC1213, MIB-II. This includes the ipNetToMediaTable (the ARP
        cache). This ipoaVcTable keeps a set of VCs for each entry in
        the ARP cache that was put there by this IP over ATM system
        acting as either a host or server. The ipoaVcTable doesn't
        augment the ipNetToMediaTable (ARP Cache) since the
        the correspondence between tables is not one-to-one."
    ::= { ipoaObjects 7 }

ipoaVcEntry OBJECT-TYPE
    SYNTAX IpoaVcEntry
    ACCESS not-accessible
    STATUS mandatory
    DESCRIPTION
        "A VC (permanent or switched) that this host or server has
        opened with another member of a LIS. Additional information
        can be determined about the VC from RFC1695, the AToM MIB.
        
        In an SVC environment, entries can not be created in
        this table by a management application. Entries are
        automatically
        added by the system as the result of ATMARP processing.
        
        In a PVC environment, an entry is automatically added to
        this table when an entry is created in the ipoaConfigPvcTable
        and the IP Address at the end of the PVC is discovered using
        In_ATMARP. An entry also is added to the ipNetToMediaTable."
    INDEX { ipNetToMediaIfIndex, ipNetToMediaNetAddress, ipoaVcVpi, ipoaVcVci }
    ::= { ipoaVcTable 1 }

IpoaVcEntry ::= SEQUENCE {
    ipoaVcVpi IpoaVpiInteger,
    ipoaVcVci IpoaVciInteger,
    ipoaVcType AtmConnKind,
    ipoaVcNegotiatedEncapsType IpoaEncapsType,
    ipoaVcNegotiatedMtu Integer32
    }

ipoaVcVpi OBJECT-TYPE
    SYNTAX IpoaVpiInteger
--    Rsyntax Integer32(0..255)
    ACCESS read-only
    STATUS mandatory
    DESCRIPTION
        "The VPI value for the Virtual Circuit."
    ::= { ipoaVcEntry 1 }

ipoaVcVci OBJECT-TYPE
    SYNTAX IpoaVciInteger
--    Rsyntax Integer32(0..65535)
    ACCESS read-only
    STATUS mandatory
    DESCRIPTION
        "The VCI value for the Virtual Circuit."
    ::= { ipoaVcEntry 2 }

ipoaVcType OBJECT-TYPE
    SYNTAX AtmConnKind
--    Rsyntax INTEGER {
--        pvc(1),
--        svcIncoming(2),
--        svcOutgoing(3),
--        spvcInitiator(4),
--        spvcTarget(5)
--        }
    ACCESS read-only
    STATUS mandatory
    DESCRIPTION
        "The type of the Virtual Circuit."
    ::= { ipoaVcEntry 3 }

ipoaVcNegotiatedEncapsType OBJECT-TYPE
    SYNTAX IpoaEncapsType
--    Rsyntax INTEGER {
--        llcSnap(1),
--        vcMuxed(2),
--        other(3)
--        }
    ACCESS read-only
    STATUS mandatory
    DESCRIPTION
        "The encapsulation type used when communicating over this
        circuit."
    ::= { ipoaVcEntry 4 }

ipoaVcNegotiatedMtu OBJECT-TYPE
    SYNTAX Integer32(0..65535)
    ACCESS read-only
    STATUS mandatory
    DESCRIPTION
        "The MTU used when communicating over this circuit."
    ::= { ipoaVcEntry 5 }

ipoaConfigPvcTable OBJECT-TYPE
    SYNTAX SEQUENCE OF IpoaConfigPvcEntry
    ACCESS not-accessible
    STATUS mandatory
    DESCRIPTION
        "This table must be supported when PVCs are intended to
        be supported in order to enable the setup of PVCs for use
        by IP."
    ::= { ipoaObjects 8 }

ipoaConfigPvcEntry OBJECT-TYPE
    SYNTAX IpoaConfigPvcEntry
    ACCESS not-accessible
    STATUS mandatory
    DESCRIPTION
        "Defines a single PVC that exists at this host for use by
        IP. "
    INDEX { ipoaConfigPvcIfIndex, ipoaConfigPvcVpi, ipoaConfigPvcVci }
    ::= { ipoaConfigPvcTable 1 }

IpoaConfigPvcEntry ::= SEQUENCE {
    ipoaConfigPvcIfIndex InterfaceIndex,
    ipoaConfigPvcVpi IpoaVpiInteger,
    ipoaConfigPvcVci IpoaVciInteger,
    ipoaConfigPvcDefaultMtu Integer32,
    ipoaConfigPvcRowStatus RowStatus
    }

ipoaConfigPvcIfIndex OBJECT-TYPE
    SYNTAX InterfaceIndex
--    Rsyntax Integer32
    ACCESS not-accessible
    STATUS mandatory
    DESCRIPTION
        "The ifIndex of the ATM Interface that this PVC
         is associated with."
    ::= { ipoaConfigPvcEntry 1 }

ipoaConfigPvcVpi OBJECT-TYPE
    SYNTAX IpoaVpiInteger
--    Rsyntax Integer32(0..255)
    ACCESS not-accessible
    STATUS mandatory
    DESCRIPTION
        "The VPI value for the Virtual Circuit."
    ::= { ipoaConfigPvcEntry 2 }

ipoaConfigPvcVci OBJECT-TYPE
    SYNTAX IpoaVciInteger
--    Rsyntax Integer32(0..65535)
    ACCESS not-accessible
    STATUS mandatory
    DESCRIPTION
        "The VCI value for the Virtual Circuit."
    ::= { ipoaConfigPvcEntry 3 }

ipoaConfigPvcDefaultMtu OBJECT-TYPE
    SYNTAX Integer32(0..65535)
    ACCESS read-write
    STATUS mandatory
    DESCRIPTION
        "Classic2 allows use of other MTU values for PVCs
        but considers the how a value other than 9180 could
        be selected to be out of scope. ipoaConfigPvcDefaultMtu
        can be used to configure the MTU to be used for the PVC.
        Both ends must have the same value configured."
    DEFVAL { 9180 }
    ::= { ipoaConfigPvcEntry 4 }

ipoaConfigPvcRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows rows to be created and deleted in the
         ipoaConfigPvcTable. Creation of a entry in this table
         should eventually result in the creation of a
        ipNetToMediaEntry
         and a corresponding ipoaVcEntry after InATMARP has
         determined the destination address of system that the
         PVC is connected to. Setting this object to destroy(6)
         should remove the corresponding ipNetToMediaTable and
         ipoaVcTable entries."
    REFERENCE
        "RFC 1903, 'Textual Conventions for version 2 of the Simple
        Network Management Protocol (SNMPv2).'"
    ::= { ipoaConfigPvcEntry 5 }

ipoaGeneralGroup OBJECT IDENTIFIER ::= { ipoaGroups 1 }
-- OBJECT-GROUP
--  Status
--    mandatory
--  Descr
--    The required objects.
--  objects
--    ipoaLisSubnetAddr, ipoaLisDefaultMtu, 
--    ipoaLisDefaultEncapsType, ipoaLisInactivityTimer, 
--    ipoaLisMinHoldingTime, ipoaLisQDepth, ipoaLisMaxCalls, 
--    ipoaLisCacheEntryAge, ipoaLisRetries, ipoaLisTimeout, 
--    ipoaLisDefaultPeakCellRate, ipoaLisActiveVcs, 
--    ipoaLisRowStatus, ipoaLisIfMappingStatus, 
--    ipoaArpRemoteSrvrRowStatus, ipoaArpRemoteSrvrIpAddr, 
--    ipoaVcVpi, ipoaVcVci, ipoaVcType, ipoaVcNegotiatedEncapsType, 
--    ipoaVcNegotiatedMtu, ipoaConfigPvcDefaultMtu, 
--    ipoaConfigPvcRowStatus

ipoaClientGroup OBJECT IDENTIFIER ::= { ipoaGroups 2 }
-- OBJECT-GROUP
--  Status
--    mandatory
--  Descr
--    This group is mandatory for all hosts where ip over
--     ATM client support is required.
--  objects
--    ipoaArpClientAtmAddr, ipoaArpClientSrvrInUse, 
--    ipoaArpClientInArpReqsIn, ipoaArpClientInArpReqsOut, 
--    ipoaArpClientInArpRepliesIn, ipoaArpClientInArpRepliesOut, 
--    ipoaArpClientInArpInvalidReqsIn, 
--    ipoaArpClientInArpInvalidReqsOut, ipoaArpClientArpReqsIn, 
--    ipoaArpClientArpReqsOut, ipoaArpClientArpRepliesIn, 
--    ipoaArpClientArpRepliesOut, ipoaArpClientArpNaksIn, 
--    ipoaArpClientArpNaksOut, ipoaArpClientArpOpUnknown, 
--    ipoaArpClientArpSrvrNoResp, ipoaArpClientRowStatus

ipoaSrvrGroup OBJECT IDENTIFIER ::= { ipoaGroups 3 }
-- OBJECT-GROUP
--  Status
--    mandatory
--  Descr
--    This group is mandatory for all hosts where ATMARP
--     servers are present.
--  objects
--    ipoaLisTrapEnable, ipoaArpSrvrLis, ipoaArpSrvrInArpReqsIn, 
--    ipoaArpSrvrInArpReqsOut, ipoaArpSrvrInArpRepliesIn, 
--    ipoaArpSrvrInArpRepliesOut, ipoaArpSrvrInArpInvalidReqsIn, 
--    ipoaArpSrvrInArpInvalidReqsOut, ipoaArpSrvrArpReqsIn, 
--    ipoaArpSrvrArpRepliesOut, ipoaArpSrvrArpNaksOut, 
--    ipoaArpSrvrArpDupIpAddr, ipoaArpSrvrArpOpUnknown, 
--    ipoaArpSrvrRowStatus

ipoaCompliance OBJECT IDENTIFIER ::= { ipoaCompliances 1 }
-- MODULE-COMPLIANCE
--  Status
--    mandatory
--  Descr
--    The compliance statement for agents that support the IPOA
--    MIB.
--  Module
--    >>current<<
--   MandGroup
--    ipoaGeneralGroup
--   OptGroup
--    ipoaClientGroup
--   OptGroup
--    ipoaSrvrGroup
--   ObjVar
--    ipoaLisDefaultMtu
--   ObjVar
--    ipoaLisDefaultEncapsType
--   ObjVar
--    ipoaLisDefaultPeakCellRate


END
