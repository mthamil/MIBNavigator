INTERNETSERVER-MIB DEFINITIONS ::= BEGIN

        IMPORTS
                enterprises,
                OBJECT-TYPE,
                Counter
                        FROM RFC1155-SMI
                microsoft, software
                        FROM MSFT-MIB;

--      microsoft       OBJECT IDENTIFIER ::= { enterprises 311 }
--      software        OBJECT IDENTIFIER ::= { microsoft 1 }
        internetServer  OBJECT IDENTIFIER ::= { software 7 }
        inetSrvCommon   OBJECT IDENTIFIER ::= { internetServer 1 }
        inetSrvStats    OBJECT IDENTIFIER ::= { inetSrvCommon 1 }

-- Internet Server Common Statistics

END
