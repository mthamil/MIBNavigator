-- MIB created 11/13/98 22:12:33, by
--   SMIC (the next generation) version 1.6.29, November 22, 1994.

TN3270E-MIB DEFINITIONS ::= BEGIN

-- From file: "tn3270e.mi2"
-- Compile options "G A T M"

IMPORTS
    TimeTicks, IpAddress, Counter32, Gauge32
            FROM SNMPv2-SMI-v1
    OBJECT-TYPE
            FROM RFC-1212
    RowStatus, DisplayString
            FROM SNMPv2-TC-v1
    snanauMIB
            FROM SNA-NAU-MIB;

tn3270eMIB OBJECT IDENTIFIER ::= { snanauMIB 8 }
-- MODULE-IDENTITY
--  LastUpdated
--    9711200000Z
--  OrgName
--    TN3270E Working Group
--  ContactInfo
--    Kenneth White (kennethw@vnet.ibm.com)
--     IBM Corp.
--  Descr
--    This module defines a portion of the management
--    information base (MIB) for managing TN3270E servers

tn3270eNotifications OBJECT IDENTIFIER ::= { tn3270eMIB 0 }
tn3270eObjects  OBJECT IDENTIFIER ::= { tn3270eMIB 1 }
tn3270eConformance OBJECT IDENTIFIER ::= { tn3270eMIB 3 }
tn3270eGroups   OBJECT IDENTIFIER ::= { tn3270eConformance 1 }
tn3270eCompliances OBJECT IDENTIFIER ::= { tn3270eConformance 2 }

SnaResourceName ::= OCTET STRING(SIZE(0..17))
-- TEXTUAL-CONVENTION
--  Status
--    mandatory
--  Descr
--    The textual convention for defining an SNA resource
--     name. A fully qualified SNA resource name, consisting of
--     a 1 to 8 character network identifier (NetId), a
--     period ('.'), and a 1 to 8 character resource name
--     (ResName).
--    
--     The NetId and ResName are constructed from the uppercase
--     letter 'A' - 'Z' and the numerics '0' - '9', all encoded
--     in ASCII, with the restriction that the first character
--     of each must be a letter. Trailing blanks are not allowed.
--    
--     Earlier versions of SNA permitted three additional
--     characters in NetIds and ResNames:  '#', '@', and '$'.
--     While this use of these characters has been retired,
--     a Management Station should still accept them for
--     backward compatibility.
--    
--     Note: This Textual Convention is not subject to
--     internationalization, and does not use the character
--     encodings used by the Utf8String Textual Convention.

Tn3270eAddrType ::= INTEGER {
        unknown(0),
        ipv4(1),
        ipv6(2)
        }
-- TEXTUAL-CONVENTION
--  Status
--    mandatory
--  Descr
--    The textual convention for defining the type of an Client
--     Address.

Tn3270ResourceType ::= INTEGER {
        other(0),
        lu(1),
        printer(2)
        }
-- TEXTUAL-CONVENTION
--  Status
--    mandatory
--  Descr
--    The type of resource defined by a resource pool. Refer
--    to tn3270eResPoolTable.

Tn3270eTAddress ::= OCTET STRING(SIZE(0..255))
-- TEXTUAL-CONVENTION
--  Status
--    mandatory
--  Descr
--    Denotes an Client Address. The type of Client Address is
--     determined by use of the Tn3270eAddrType Textual Convention.
--     The length in octets of a Tn3270eTAddress object is:
--    
--      Tn3270eAddrType ENUM
--           unknown(0)             not known, must look at the
--                                  actual length of the
--                                  Tn3270eTAddress OCTET STRING.
--           ipv4(1)                4 OCTETS
--           ipv6(2)                16 OCTETS
--    
--    This textual convention is similar to the TAddress TC
--    defined by RFC1903 except that it allows a zero length
--    OCTET STRING and is not a full transport layer address.

Tn3270Functions ::= OCTET STRING(SIZE(2))
-- TEXTUAL-CONVENTION
--  Status
--    mandatory
--  Descr
--    This textual convention is intended to reflect the
--    current set of TN3270 and TN3270E functions that can
--    be negotiated between a server and its client:
--    
--    RFC856
--    transmitBinary    The sender of this command REQUESTS
--                      permission to begin transmitting, or
--                      confirms that it will now begin transmitting
--                      characters which are to be interpreted
--                      as 8 bits of binary data by
--                      the receiver of the data.
--    RFC820
--    timeMark         The sender of this command REQUESTS that
--                     the receiver of this command return a WILL
--                     TIMING-MARK in the data stream at the
--                     'appropriate place' ...
--    RFC885
--    endOfRecord      The sender of this command requests
--                     permission to begin transmission of the
--                     Telnet END-OF-RECORD (EOR) code when
--                     transmitting data characters, or
--                     the sender of this command confirms it will
--                     now begin transmission of EORs with
--                     transmitted data characters.
--    RFC1091
--    terminalType     Sender is willing to send terminal type
--                     information in a subsequent sub-negotiation.
--    RFC1041
--    tn3270Regime     Sender is willing to send list of supported
--                     3270 Regimes in a subsequent sub-negotiation.
--    RFC1647
--    scsCtlCodes     (Printer sessions only).  Allows the use
--                    of the SNA Character Stream (SCS) and SCS
--                    control codes on the session.  SCS is
--                    used with LU type 1 SNA sessions.
--    dataStreamCtl   (Printer sessions only).  Allows the use
--                    of the standard 3270 data stream.  This
--                    corresponds to LU type 3 SNA sessions.
--    responses       Provides support for positive and
--                    negative response handling.  Allows the
--                    server to reflect to the client any and
--                    all definite, exception, and no response
--                    requests sent by the host application.
--    bindImage       Allows the server to send the SNA Bind
--                    image and Unbind notification to the
--                    client.
--    sysreq          Allows the client and server to emulate
--                    some (or all, depending on the server) of
--                    the functions of the SYSREQ key in an SNA
--                    environment.

Tn3270DeviceTypes ::= INTEGER {
        unknown(0),
        ibm3278d2(1),
        ibm3278d2E(2),
        ibm3278d3(3),
        ibm3278d3E(4),
        ibm3278d4(5),
        ibm3278d4E(6),
        ibm3278d5(7),
        ibm3278d5E(8),
        ibmDynamic(9),
        ibm3287d1(10)
        }
-- TEXTUAL-CONVENTION
--  Status
--    mandatory
--  Descr
--    This textual convention defines the list of device types
--    that can be set as defined by RFC 1647.

tn3270eSrvrConfTable OBJECT-TYPE
    SYNTAX SEQUENCE OF Tn3270eSrvrConfEntry
    ACCESS not-accessible
    STATUS mandatory
    DESCRIPTION
        "This table defines the configuration elements for
        TN3270E Servers. The number of entries in this table
        is expected to vary depending on the location of the
        table. A particular TN3270E server is expected to
        have a single entry. Modeling of the configuration
        elements as a table allows multiple
        TN3270E Servers to exist at the same host."
    ::= { tn3270eObjects 1 }

tn3270eSrvrConfEntry OBJECT-TYPE
    SYNTAX Tn3270eSrvrConfEntry
    ACCESS not-accessible
    STATUS mandatory
    DESCRIPTION
        "Definition of the configuration elements for a single
        TN3270E server."
    INDEX { tn3270eSrvrConfIndex }
    ::= { tn3270eSrvrConfTable 1 }

Tn3270eSrvrConfEntry ::= SEQUENCE {
    tn3270eSrvrConfIndex UInteger32,
    tn3270eSrvrConfInactivityTimeout UInteger32,
    tn3270eSrvrConfActivityCheck INTEGER,
    tn3270eSrvrConfActivityTimeout UInteger32,
    tn3270eSrvrConfActivityInterval UInteger32,
    tn3270eSrvrFunctionsSupported Tn3270Functions,
    tn3270eSrvrConfAdminStatus INTEGER,
    tn3270eSrvrConfOperStatus INTEGER,
    tn3270eSrvrConfSessionTermState INTEGER,
    tn3270eSrvrConfSrvrType INTEGER,
    tn3270eSrvrConfContact DisplayString,
    tn3270eSrvrConfRowStatus RowStatus
    }

tn3270eSrvrConfIndex OBJECT-TYPE
    SYNTAX UInteger32
    ACCESS not-accessible
    STATUS mandatory
    DESCRIPTION
        "Indicates the instance of a TN3270E server that
         exists at an IP Host. Assignments of tn3270eSrvrConfIndex
         values need not be continuous and is implementation
         dependent. Within a host, assignment of
         tn3270eSrvrConfIndex values must be unique."
    ::= { tn3270eSrvrConfEntry 1 }

tn3270eSrvrConfInactivityTimeout OBJECT-TYPE
    SYNTAX UInteger32(0..99999999)
--  Units
--    seconds
    ACCESS read-write
    STATUS mandatory
    DESCRIPTION
        "The inactivity time-out specified in seconds. When a
         connection has been inactive for the number of seconds
         specified by this object it is closed. The default of
         0 means no inactivity time-out."
    DEFVAL { 0 }
    ::= { tn3270eSrvrConfEntry 2 }

tn3270eSrvrConfActivityCheck OBJECT-TYPE
    SYNTAX INTEGER {
        noCheck(0),
        timeMark(1),
        nop(2)
        }
    ACCESS read-write
    STATUS mandatory
    DESCRIPTION
        "This object is intended to enable either timemark or
         nop processing."
    DEFVAL { noCheck }
    ::= { tn3270eSrvrConfEntry 3 }

tn3270eSrvrConfActivityTimeout OBJECT-TYPE
    SYNTAX UInteger32(1..99999999)
--  Units
--    seconds
    ACCESS read-write
    STATUS mandatory
    DESCRIPTION
        "The TIMEMARK or NOP processing time-out specified in seconds.
         Note that a value of 0 is not allowed for this object since
         the function that uses this object relies on
         tn3270eSrvrConfActivityCheck for function enablement."
    DEFVAL { 600 }
    ::= { tn3270eSrvrConfEntry 4 }

tn3270eSrvrConfActivityInterval OBJECT-TYPE
    SYNTAX UInteger32(1..99999999)
--  Units
--    seconds
    ACCESS read-write
    STATUS mandatory
    DESCRIPTION
        "The scan interval to be used by a TN3270E server.
         TIMEMARK or NOP processing scans the Telnet sessions
         on the interval provided by this object looking for
         sessions that have been idle for more than the value
         provided by tn3270eSrvrConfActivityTimeout.
         Note that a value of 0 is not allowed for this object since
         the function that uses this object relies on
         tn3270eSrvrConfActivityCheck for function enablement."
    DEFVAL { 120 }
    ::= { tn3270eSrvrConfEntry 5 }

tn3270eSrvrFunctionsSupported OBJECT-TYPE
    SYNTAX Tn3270Functions
--    Rsyntax OCTET STRING(SIZE(2))
    ACCESS read-only
    STATUS mandatory
    DESCRIPTION
        "This object indicates the functions supported by a
         TN3270E server."
    ::= { tn3270eSrvrConfEntry 6 }

tn3270eSrvrConfAdminStatus OBJECT-TYPE
    SYNTAX INTEGER {
        up(1),
        down(2),
        stopImmediate(3)
        }
    ACCESS read-write
    STATUS mandatory
    DESCRIPTION
        "The desired state of the TN3270E server:
        
         up(1)            - Activate a TN3270E server.
         down(2)          - Informs the associating TN3270E server
                            to gracefully terminate its processing.
         stopImmediate(3) - Informs the associating TN3270E server
                            to terminate immediately.
        
         Implementation as to the exact semantics of either down(2)
         or stopImmediate(3) processing is left as implementation
         dependent. A TN3270E server that does not distinguish
         between down or stopImmediate transitions should not
         support stopImmediate."
    ::= { tn3270eSrvrConfEntry 7 }

tn3270eSrvrConfOperStatus OBJECT-TYPE
    SYNTAX INTEGER {
        up(1),
        down(2)
        }
    ACCESS read-only
    STATUS mandatory
    DESCRIPTION
        "The current operational state of a TN3270E server:
        
         up(1)   - The corresponding TN3270E server is active.
         down(2) - The corresponding TN3270E server is inactive."
    ::= { tn3270eSrvrConfEntry 8 }

tn3270eSrvrConfSessionTermState OBJECT-TYPE
    SYNTAX INTEGER {
        terminate(1),
        luSessionPend(2),
        queueSession(3)
        }
    ACCESS read-write
    STATUS mandatory
    DESCRIPTION
        "The current state for determining what a TN3270E server
         should do when a TN3270 Session terminates:
        
        terminate(1)     => Terminate TCP connection.
        luSessionPend(2) => Do not drop the TCP Connection
                            associated with a client when their
                            TN3270 Session ends. Processing should
                            redrive session initialization as if the
                            client was first connecting.
        queueSession(3)  => QUEUESESSION deals with CLSDST-Pass.
                            An example is the easiest explanation.
                            Assume APPL1 does a CLSDST-Pass
                            to APPL2.  Then the client logs off APPL
                            Without QUEUESESSION the connection
                            would now be broken. With QUEUESESSION
                            the TN3270E server keeps the LU around
                            after getting the APPL2 unbind waiting
                            for a bind from APPL1."
    DEFVAL { terminate }
    ::= { tn3270eSrvrConfEntry 9 }

tn3270eSrvrConfSrvrType OBJECT-TYPE
    SYNTAX INTEGER {
        unknown(0),
        host(1),
        gateway(2)
        }
    ACCESS read-only
    STATUS mandatory
    DESCRIPTION
        "This object indicates the type of TN3270E server.
        The existence of MIB tables and objects that will be
        defined by follow-on MIBs may be predicated on whether the
        TN3270E server can be local to the same host as a
        Target Application (host(1)) or will always be remote
        (gateway(2))."
    ::= { tn3270eSrvrConfEntry 10 }

tn3270eSrvrConfContact OBJECT-TYPE
    SYNTAX DisplayString(SIZE(0..255))
--    Rsyntax OCTET STRING(SIZE(0..255))
    ACCESS read-write
    STATUS mandatory
    DESCRIPTION
        "This object provides a scratch pad for a TN3270E server
        administrator for storing information for later retrieval."
    ::= { tn3270eSrvrConfEntry 11 }

tn3270eSrvrConfRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted in the
        tn3270eSrvrConfTable.
        
        An entry in this table is deleted by setting this object
        to destroy(6)."
    REFERENCE
        "RFC 1903, 'Textual Conventions for version 2 of the Simple
        Network Management Protocol (SNMPv2).'"
    ::= { tn3270eSrvrConfEntry 12 }

tn3270eSrvrPortTable OBJECT-TYPE
    SYNTAX SEQUENCE OF Tn3270eSrvrPortEntry
    ACCESS not-accessible
    STATUS mandatory
    DESCRIPTION
        "This table defines the TCP ports associated with TN3270E
        Servers."
    ::= { tn3270eObjects 2 }

tn3270eSrvrPortEntry OBJECT-TYPE
    SYNTAX Tn3270eSrvrPortEntry
    ACCESS not-accessible
    STATUS mandatory
    DESCRIPTION
        "Definition of a single TCP port assignment to a
         TN3270E server."
    INDEX { tn3270eSrvrConfIndex, tn3270eSrvrPort, tn3270eSrvrPortAddrType, tn3270eSrvrPortAddress }
    ::= { tn3270eSrvrPortTable 1 }

Tn3270eSrvrPortEntry ::= SEQUENCE {
    tn3270eSrvrPort UInteger32,
    tn3270eSrvrPortAddrType Tn3270eAddrType,
    tn3270eSrvrPortAddress Tn3270eTAddress,
    tn3270eSrvrPortRowStatus RowStatus
    }

tn3270eSrvrPort OBJECT-TYPE
    SYNTAX UInteger32(0..65535)
    ACCESS not-accessible
    STATUS mandatory
    DESCRIPTION
        "Indicates a port assigned to a server."
    ::= { tn3270eSrvrPortEntry 1 }

tn3270eSrvrPortAddrType OBJECT-TYPE
    SYNTAX Tn3270eAddrType
--    Rsyntax INTEGER {
--        unknown(0),
--        ipv4(1),
--        ipv6(2)
--        }
    ACCESS not-accessible
    STATUS mandatory
    DESCRIPTION
        "Indicates the type of the Client Address represented in
         tn3270eSrvrPortAddress."
    ::= { tn3270eSrvrPortEntry 2 }

tn3270eSrvrPortAddress OBJECT-TYPE
    SYNTAX Tn3270eTAddress
--    Rsyntax OCTET STRING(SIZE(0..255))
    ACCESS not-accessible
    STATUS mandatory
    DESCRIPTION
        "The Client Address associated with a TN3270E server port.
         tn3270eClientGroupAddrType indicates the address type
         (ipv4 or ipv6 for example)."
    ::= { tn3270eSrvrPortEntry 3 }

tn3270eSrvrPortRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted in the
        tn3270eSrvrPortTable.
        
        An entry in this table is deleted by setting this object
        to destroy(6)."
    REFERENCE
        "RFC 1903, 'Textual Conventions for version 2 of the Simple
        Network Management Protocol (SNMPv2).'"
    ::= { tn3270eSrvrPortEntry 4 }

tn3270eSrvrStatsTable OBJECT-TYPE
    SYNTAX SEQUENCE OF Tn3270eSrvrStatsEntry
    ACCESS not-accessible
    STATUS mandatory
    DESCRIPTION
        "This table defines a set of statistics concerning
        global TN3270E server performance."
    ::= { tn3270eObjects 3 }

tn3270eSrvrStatsEntry OBJECT-TYPE
    SYNTAX Tn3270eSrvrStatsEntry
    ACCESS not-accessible
    STATUS mandatory
    DESCRIPTION
        "A collection of statistical and maximum usage objects
        for a single TN3270 server.  An entry can represent the total
        activity of the server, or it can represent the activity
        occurring at the server on either a port or a
        port-and-local-address basis.
        
        Collection of the statistics represented by the objects
        in this table is not mandatory.   An implementation
        of this table MUST use only one of the three levels of
        refinement that this table supports for the entries
        associated with each TN3270E server.
        
        The indexing for a row that represents total server
        statistics is as follows:
        
             tn3270eSrvrConfIndex      value identifying the server
             tn3270eSrvrStatsPort      0
             tn3270eSrvrPortAddrType   unknown(0)
             tn3270eSrvrPortAddress    zero-length octet string.
        
        On a port basis:
        
             tn3270eSrvrConfIndex      value identifying the server
             tn3270eSrvrStatsPort      > 0
             tn3270eSrvrPortAddrType   unknown(0)
             tn3270eSrvrPortAddress    zero-length octet string.
        
        On a port-and-local-address basis:
        
             tn3270eSrvrConfIndex      value identifying the server
             tn3270eSrvrStatsPort      > 0
             tn3270eSrvrPortAddrType   valid value other than unknown(0)
             tn3270eSrvrPortAddress    non-zero-length octet string.
        "
    INDEX { tn3270eSrvrConfIndex, tn3270eSrvrStatsPort, tn3270eSrvrPortAddrType, tn3270eSrvrPortAddress }
    ::= { tn3270eSrvrStatsTable 1 }

Tn3270eSrvrStatsEntry ::= SEQUENCE {
    tn3270eSrvrStatsPort UInteger32,
    tn3270eSrvrStatsUpTime TimeTicks,
    tn3270eSrvrStatsMaxLus UInteger32,
    tn3270eSrvrStatsLusInUse Gauge32,
    tn3270eSrvrStatsSpareLus Gauge32,
    tn3270eSrvrStatsMaxPtrs UInteger32,
    tn3270eSrvrStatsPtrsInUse Gauge32,
    tn3270eSrvrStatsSparePtrs Gauge32,
    tn3270eSrvrStatsConnectsIn Counter32,
    tn3270eSrvrStatsConnRejects Counter32,
    tn3270eSrvrStatsDisconnects Counter32,
    tn3270eSrvrStatsOctetsIn Counter64,
    tn3270eSrvrStatsOctetsInLow Counter32,
    tn3270eSrvrStatsOctetsOut Counter64,
    tn3270eSrvrStatsOctetsOutLow Counter32
    }

tn3270eSrvrStatsPort OBJECT-TYPE
    SYNTAX UInteger32(0..65535)
    ACCESS not-accessible
    STATUS mandatory
    DESCRIPTION
        "Indicates the port that the corresponding statistics are
         for. Implementation of collection of these statistics
         on a port basis is not mandatory. An implementation may
         limit itself to keeping this data on a global basis by
         using a value of 0."
    ::= { tn3270eSrvrStatsEntry 1 }

tn3270eSrvrStatsUpTime OBJECT-TYPE
    SYNTAX TimeTicks
    ACCESS read-only
    STATUS mandatory
    DESCRIPTION
        "Indicates when either usage of a associating port becomes
         active (tn3270eSrvrStatsPort non-zero) or if the entry
         is being kept on a global basis the time that the TN3270E
         server becomes active.  The value of this object does not
         get reset based on port usage status changes or changes
         to tn3270eSrvrConfOperStatus."
    ::= { tn3270eSrvrStatsEntry 2 }

tn3270eSrvrStatsMaxLus OBJECT-TYPE
    SYNTAX UInteger32
    ACCESS read-only
    STATUS mandatory
    DESCRIPTION
        "Indicates the maximum number of LUs for use by a
         TN3270E server. The granularity of this data can be
         either global (corresponding tn3270eSrvrStatsPort index
         equal to 0) or on a port basis."
    ::= { tn3270eSrvrStatsEntry 3 }

tn3270eSrvrStatsLusInUse OBJECT-TYPE
    SYNTAX Gauge32
    ACCESS read-only
    STATUS mandatory
    DESCRIPTION
        "Indicates the current number of LUs in use by a
         TN3270E server. The granularity of this data can be
         either global (corresponding tn3270eSrvrStatsPort index
         equal to 0) or on a port basis."
    ::= { tn3270eSrvrStatsEntry 4 }

tn3270eSrvrStatsSpareLus OBJECT-TYPE
    SYNTAX Gauge32
    ACCESS read-only
    STATUS mandatory
    DESCRIPTION
        "Indicates the number of free LUs for a particular TN3270E
         server. It is possible that the difference between
         tn3270eSrvrStatsMaxLus and tn3270eSrvrStatsLusInUse does
         not equal tn3270eSrvrStatsSpareLus. An LU may exist
         but not be useable by an client connection.
         The granularity of this data can be
         either global (corresponding tn3270eSrvrStatsPort index
         equal to 0) or on a port basis."
    ::= { tn3270eSrvrStatsEntry 5 }

tn3270eSrvrStatsMaxPtrs OBJECT-TYPE
    SYNTAX UInteger32
    ACCESS read-only
    STATUS mandatory
    DESCRIPTION
        "Indicates the maximum number of Printer Resources for
         use by a TN3270E server. The granularity of this data
         can be either global (corresponding tn3270eSrvrStatsPort
         index equal to 0) or on a port basis."
    ::= { tn3270eSrvrStatsEntry 6 }

tn3270eSrvrStatsPtrsInUse OBJECT-TYPE
    SYNTAX Gauge32
    ACCESS read-only
    STATUS mandatory
    DESCRIPTION
        "Indicates the current number of Printer Resources in
         use by a TN3270E server. The granularity of this data
         can be either global (corresponding tn3270eSrvrStatsPort
         index equal to 0) or on a port basis."
    ::= { tn3270eSrvrStatsEntry 7 }

tn3270eSrvrStatsSparePtrs OBJECT-TYPE
    SYNTAX Gauge32
    ACCESS read-only
    STATUS mandatory
    DESCRIPTION
        "Indicates the number of free Printer Resources for a
         particular TN3270E server. It is possible that the
         difference between tn3270eSrvrStatsMaxPtrs and
         tn3270eSrvrStatsPtrsInUse does not equal
         tn3270eSrvrStatsSparePtrs. A Printer resource may
         exist but not be useable by an client connection.
         The granularity of this data
         can be either global (corresponding tn3270eSrvrStatsPort
         index equal to 0) or on a port basis."
    ::= { tn3270eSrvrStatsEntry 8 }

tn3270eSrvrStatsConnectsIn OBJECT-TYPE
    SYNTAX Counter32
    ACCESS read-only
    STATUS mandatory
    DESCRIPTION
        "Indicates the number of client connections received by a
         TN3270E server. The granularity of this data
         can be either global (corresponding tn3270eSrvrStatsPort
         index equal to 0) or on a port basis."
    ::= { tn3270eSrvrStatsEntry 9 }

tn3270eSrvrStatsConnRejects OBJECT-TYPE
    SYNTAX Counter32
    ACCESS read-only
    STATUS mandatory
    DESCRIPTION
        "Indicates the number of client connections rejected during
         connection setup. An example of this is when no LU or
         Printer resource is available to associate with the
         TCP Connection of an client. The granularity of this data
         can be either global (corresponding tn3270eSrvrStatsPort
         index equal to 0) or on a port basis."
    ::= { tn3270eSrvrStatsEntry 10 }

tn3270eSrvrStatsDisconnects OBJECT-TYPE
    SYNTAX Counter32
    ACCESS read-only
    STATUS mandatory
    DESCRIPTION
        "Indicates the number of client connections disconnected by a
         TN3270E server. The granularity of this data
         can be either global (corresponding tn3270eSrvrStatsPort
         index equal to 0) or on a port basis."
    ::= { tn3270eSrvrStatsEntry 11 }

tn3270eSrvrStatsOctetsIn OBJECT-TYPE
    SYNTAX Counter64
    ACCESS read-only
    STATUS mandatory
    DESCRIPTION
        "Indicates the number of octets received from TN3270
         and TN3270E Clients.  The granularity
         of this data  can be either global (corresponding
         tn3270eSrvrStatsPort index equal to 0) or on a port basis."
    ::= { tn3270eSrvrStatsEntry 12 }

tn3270eSrvrStatsOctetsInLow OBJECT-TYPE
    SYNTAX Counter32
    ACCESS read-only
    STATUS mandatory
    DESCRIPTION
        "Low order 32 bits of tn3270eSrvrStatsOctetsIn."
    ::= { tn3270eSrvrStatsEntry 13 }

tn3270eSrvrStatsOctetsOut OBJECT-TYPE
    SYNTAX Counter64
    ACCESS read-only
    STATUS mandatory
    DESCRIPTION
        "Indicates the number of octets sent to TN3270
         and TN3270E Clients. The granularity
         of this data  can be either global (corresponding
         tn3270eSrvrStatsPort index equal to 0) or on a port basis."
    ::= { tn3270eSrvrStatsEntry 14 }

tn3270eSrvrStatsOctetsOutLow OBJECT-TYPE
    SYNTAX Counter32
    ACCESS read-only
    STATUS mandatory
    DESCRIPTION
        "Low order 32 bits of tn3270eSrvrStatsOctetsOut."
    ::= { tn3270eSrvrStatsEntry 15 }

tn3270eClientGroupTable OBJECT-TYPE
    SYNTAX SEQUENCE OF Tn3270eClientGroupEntry
    ACCESS not-accessible
    STATUS mandatory
    DESCRIPTION
        "This table defines client address groupings for use by a
        TN3270E server."
    ::= { tn3270eObjects 4 }

tn3270eClientGroupEntry OBJECT-TYPE
    SYNTAX Tn3270eClientGroupEntry
    ACCESS not-accessible
    STATUS mandatory
    DESCRIPTION
        "Definition of a single client address entry. All entries with
        the same first two indexes, tn3270eSrvrConfIndex and
        tn3270eClientGroupName, are considered to be in the same
        client group."
    INDEX { tn3270eSrvrConfIndex, tn3270eClientGroupName, tn3270eClientGroupAddrType, tn3270eClientGroupAddress }
    ::= { tn3270eClientGroupTable 1 }

Tn3270eClientGroupEntry ::= SEQUENCE {
    tn3270eClientGroupName DisplayString,
    tn3270eClientGroupAddrType Tn3270eAddrType,
    tn3270eClientGroupAddress Tn3270eTAddress,
    tn3270eClientGroupSubnetMask IpAddress,
    tn3270eClientGroupPfxLength UInteger32,
    tn3270eClientGroupRowStatus RowStatus
    }

tn3270eClientGroupName OBJECT-TYPE
    SYNTAX DisplayString(SIZE(1..24))
--    Rsyntax OCTET STRING(SIZE(1..24))
    ACCESS not-accessible
    STATUS mandatory
    DESCRIPTION
        "The name of a client group."
    ::= { tn3270eClientGroupEntry 1 }

tn3270eClientGroupAddrType OBJECT-TYPE
    SYNTAX Tn3270eAddrType
--    Rsyntax INTEGER {
--        unknown(0),
--        ipv4(1),
--        ipv6(2)
--        }
    ACCESS not-accessible
    STATUS mandatory
    DESCRIPTION
        "Indicates the type of the address represented in
         tn3270eClientGroupAddress."
    ::= { tn3270eClientGroupEntry 2 }

tn3270eClientGroupAddress OBJECT-TYPE
    SYNTAX Tn3270eTAddress
--    Rsyntax OCTET STRING(SIZE(0..255))
    ACCESS not-accessible
    STATUS mandatory
    DESCRIPTION
        "The client address of a member of a client group. The value
         of tn3270eClientGroupAddrType indicates the address
         type (ipv4 or ipv6 for example)."
    ::= { tn3270eClientGroupEntry 3 }

tn3270eClientGroupSubnetMask OBJECT-TYPE
    SYNTAX IpAddress
    ACCESS read-write
    STATUS mandatory
    DESCRIPTION
        "The corresponding subnet mask associated with
         tn3270eClientGroupAddress. A single IP Address is
         represented by having this object contain the value
         of 255.255.255.255. This object is valid only if
         tn3270eClientGroupAddrType has a value of ipv4(1)."
    ::= { tn3270eClientGroupEntry 4 }

tn3270eClientGroupPfxLength OBJECT-TYPE
    SYNTAX UInteger32(0..128)
    ACCESS read-write
    STATUS mandatory
    DESCRIPTION
        "The corresponding IPv6 network prefix length. This
         object is valid only if tn3270eClientGroupAddrType
         has a value of ipv6(2)."
    DEFVAL { 0 }
    ::= { tn3270eClientGroupEntry 5 }

tn3270eClientGroupRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted in the
        tn3270eClientGroupTable.
        
        An entry in this table is deleted by setting this object
        to destroy(6)."
    REFERENCE
        "RFC 1903, 'Textual Conventions for version 2 of the Simple
        Network Management Protocol (SNMPv2).'"
    ::= { tn3270eClientGroupEntry 6 }

tn3270eResPoolTable OBJECT-TYPE
    SYNTAX SEQUENCE OF Tn3270eResPoolEntry
    ACCESS not-accessible
    STATUS mandatory
    DESCRIPTION
        "This table defines resource groupings; the term
         'pool' is used as it is defined by RFC 1647."
    ::= { tn3270eObjects 5 }

tn3270eResPoolEntry OBJECT-TYPE
    SYNTAX Tn3270eResPoolEntry
    ACCESS not-accessible
    STATUS mandatory
    DESCRIPTION
        "Definition of a single resource pool member. All entries
        with the same first two indexes, tn3270eSrvrConfIndex and
        tn3270eResPoolName, are considered to be in the same pool."
    INDEX { tn3270eSrvrConfIndex, tn3270eResPoolName, tn3270eResPoolElementName }
    ::= { tn3270eResPoolTable 1 }

Tn3270eResPoolEntry ::= SEQUENCE {
    tn3270eResPoolName DisplayString,
    tn3270eResPoolElementName SnaResourceName,
    tn3270eResPoolElementType Tn3270ResourceType,
    tn3270eResPoolRowStatus RowStatus
    }

tn3270eResPoolName OBJECT-TYPE
    SYNTAX DisplayString(SIZE(1..24))
--    Rsyntax OCTET STRING(SIZE(1..24))
    ACCESS not-accessible
    STATUS mandatory
    DESCRIPTION
        "The name of a resource pool.."
    ::= { tn3270eResPoolEntry 1 }

tn3270eResPoolElementName OBJECT-TYPE
    SYNTAX SnaResourceName
--    Rsyntax OCTET STRING(SIZE(0..17))
    ACCESS not-accessible
    STATUS mandatory
    DESCRIPTION
        "The name of a member of a resource pool."
    ::= { tn3270eResPoolEntry 2 }

tn3270eResPoolElementType OBJECT-TYPE
    SYNTAX Tn3270ResourceType
--    Rsyntax INTEGER {
--        other(0),
--        lu(1),
--        printer(2)
--        }
    ACCESS read-write
    STATUS mandatory
    DESCRIPTION
        "The type of the entity in a resource pool."
    ::= { tn3270eResPoolEntry 3 }

tn3270eResPoolRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted in the
        tn3270eResPoolTable.
        
        An entry in this table is deleted by setting this object
        to destroy(6)."
    REFERENCE
        "RFC 1903, 'Textual Conventions for version 2 of the Simple
        Network Management Protocol (SNMPv2).'"
    ::= { tn3270eResPoolEntry 4 }

tn3270eSnaMapTable OBJECT-TYPE
    SYNTAX SEQUENCE OF Tn3270eSnaMapEntry
    ACCESS not-accessible
    STATUS mandatory
    DESCRIPTION
        "This table provide a mapping from the name by which
         a secondary LU is known in the SNA network to the
         name by which it is known locally at the TN3270e
         server.  This latter name serves as an index into
         the tn3270eResPoolTable and the tn3270eResMapTable."
    ::= { tn3270eObjects 6 }

tn3270eSnaMapEntry OBJECT-TYPE
    SYNTAX Tn3270eSnaMapEntry
    ACCESS not-accessible
    STATUS mandatory
    DESCRIPTION
        "Definition of a single mapping from an SSCP-supplied
         SLU name to a local SLU name."
    INDEX { tn3270eSrvrConfIndex, tn3270eSnaMapSscpSuppliedName }
    ::= { tn3270eSnaMapTable 1 }

Tn3270eSnaMapEntry ::= SEQUENCE {
    tn3270eSnaMapSscpSuppliedName SnaResourceName,
    tn3270eSnaMapLocalName SnaResourceName,
    tn3270eSnaMapPrimaryLuName SnaResourceName
    }

tn3270eSnaMapSscpSuppliedName OBJECT-TYPE
    SYNTAX SnaResourceName
--    Rsyntax OCTET STRING(SIZE(0..17))
    ACCESS not-accessible
    STATUS mandatory
    DESCRIPTION
        "The name of the secondary LU (SLU) as it is known in the
         SNA network.  This name is sent by the SSCP on the
         Activate Logical Unit (ACTLU) request."
    ::= { tn3270eSnaMapEntry 1 }

tn3270eSnaMapLocalName OBJECT-TYPE
    SYNTAX SnaResourceName
--    Rsyntax OCTET STRING(SIZE(0..17))
    ACCESS read-only
    STATUS mandatory
    DESCRIPTION
        "The local name of the secondary LU (SLU)."
    ::= { tn3270eSnaMapEntry 2 }

tn3270eSnaMapPrimaryLuName OBJECT-TYPE
    SYNTAX SnaResourceName
--    Rsyntax OCTET STRING(SIZE(0..17))
    ACCESS read-only
    STATUS mandatory
    DESCRIPTION
        "When there is a currently active LU-LU session for this
        connection, this object returns the primary LU (PLU) name
        from the BIND.  When there is no active LU-LU session, or
        when the PLU name is unavailable for some other reason,
        this object returns the empty string."
    ::= { tn3270eSnaMapEntry 3 }

tn3270eClientResMapTable OBJECT-TYPE
    SYNTAX SEQUENCE OF Tn3270eClientResMapEntry
    ACCESS not-accessible
    STATUS mandatory
    DESCRIPTION
        "This table defines resource pool to client group mappings.
         Since both the resource pool name and client group name
         are included in the index clause of this table, multiple
         resource pools can be assigned to the same client group. This
         enables use of multiple resource pools for use in client to
         resource mapping. Assigning multiple client Groups to the
         same resource pool is also allowed, but is not the primary
         purpose for how the indexing is structured.
        
         Assignment of a resource pool to client group can be
         restricted based on TCP port. An index value of 0 for
         tn3270eClientResMapClientPort disables restriction of
         resource assignment based on client target port selection."
    ::= { tn3270eObjects 7 }

tn3270eClientResMapEntry OBJECT-TYPE
    SYNTAX Tn3270eClientResMapEntry
    ACCESS not-accessible
    STATUS mandatory
    DESCRIPTION
        "Definition of a single resource pool to client group mapping."
    INDEX { tn3270eSrvrConfIndex, tn3270eClientResMapPoolName, tn3270eClientResMapClientGroupName, tn3270eClientResMapClientPort }
    ::= { tn3270eClientResMapTable 1 }

Tn3270eClientResMapEntry ::= SEQUENCE {
    tn3270eClientResMapPoolName DisplayString,
    tn3270eClientResMapClientGroupName DisplayString,
    tn3270eClientResMapClientPort UInteger32,
    tn3270eClientResMapRowStatus RowStatus
    }

tn3270eClientResMapPoolName OBJECT-TYPE
    SYNTAX DisplayString(SIZE(1..24))
--    Rsyntax OCTET STRING(SIZE(1..24))
    ACCESS not-accessible
    STATUS mandatory
    DESCRIPTION
        "The name of a resource pool."
    ::= { tn3270eClientResMapEntry 1 }

tn3270eClientResMapClientGroupName OBJECT-TYPE
    SYNTAX DisplayString(SIZE(1..24))
--    Rsyntax OCTET STRING(SIZE(1..24))
    ACCESS not-accessible
    STATUS mandatory
    DESCRIPTION
        "The name of the client group that is mapped to a
         resource pool."
    ::= { tn3270eClientResMapEntry 2 }

tn3270eClientResMapClientPort OBJECT-TYPE
    SYNTAX UInteger32(0..65535)
    ACCESS not-accessible
    STATUS mandatory
    DESCRIPTION
        "The port to restrict a resource pool to a client group
         mapping. A value of 0 for this objects implies that
         the mapping is not restricted."
    ::= { tn3270eClientResMapEntry 3 }

tn3270eClientResMapRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted in the
        tn3270eClientResMapTable.
        
        An entry in this table is deleted by setting this object
        to destroy(6)."
    REFERENCE
        "RFC 1903, 'Textual Conventions for version 2 of the Simple
        Network Management Protocol (SNMPv2).'"
    ::= { tn3270eClientResMapEntry 4 }

tn3270eResMapTable OBJECT-TYPE
    SYNTAX SEQUENCE OF Tn3270eResMapEntry
    ACCESS not-accessible
    STATUS mandatory
    DESCRIPTION
        "This table defines the actual mapping of a resource to
         a client Address."
    ::= { tn3270eObjects 8 }

tn3270eResMapEntry OBJECT-TYPE
    SYNTAX Tn3270eResMapEntry
    ACCESS not-accessible
    STATUS mandatory
    DESCRIPTION
        "Definition of the mapping of a Resource Element to
         a client Address."
    INDEX { tn3270eSrvrConfIndex, tn3270eResMapElementName }
    ::= { tn3270eResMapTable 1 }

Tn3270eResMapEntry ::= SEQUENCE {
    tn3270eResMapElementName SnaResourceName,
    tn3270eResMapAddrType Tn3270eAddrType,
    tn3270eResMapAddress Tn3270eTAddress,
    tn3270eResMapPort UInteger32,
    tn3270eResMapElementType Tn3270ResourceType,
    tn3270eResMapSscpSuppliedName SnaResourceName
    }

tn3270eResMapElementName OBJECT-TYPE
    SYNTAX SnaResourceName
--    Rsyntax OCTET STRING(SIZE(0..17))
    ACCESS not-accessible
    STATUS mandatory
    DESCRIPTION
        "The name of a resource element.  This is the name by
        which the server implementing this table knows the
        resource.  It may be different from the name by which
        the resource is known in the SNA network.  In this case
        the name by which the resource is known in the SNA
        network is returned in the tn3270eResMapSscpSuppliedName
        object."
    ::= { tn3270eResMapEntry 1 }

tn3270eResMapAddrType OBJECT-TYPE
    SYNTAX Tn3270eAddrType
--    Rsyntax INTEGER {
--        unknown(0),
--        ipv4(1),
--        ipv6(2)
--        }
    ACCESS read-only
    STATUS mandatory
    DESCRIPTION
        "Indicates the type of the client Address represented in
         tn3270eResMapAddress."
    ::= { tn3270eResMapEntry 2 }

tn3270eResMapAddress OBJECT-TYPE
    SYNTAX Tn3270eTAddress
--    Rsyntax OCTET STRING(SIZE(0..255))
    ACCESS read-only
    STATUS mandatory
    DESCRIPTION
        "A client address."
    ::= { tn3270eResMapEntry 3 }

tn3270eResMapPort OBJECT-TYPE
    SYNTAX UInteger32(0..65535)
    ACCESS read-only
    STATUS mandatory
    DESCRIPTION
        "A client Port."
    ::= { tn3270eResMapEntry 4 }

tn3270eResMapElementType OBJECT-TYPE
    SYNTAX Tn3270ResourceType
--    Rsyntax INTEGER {
--        other(0),
--        lu(1),
--        printer(2)
--        }
    ACCESS read-only
    STATUS mandatory
    DESCRIPTION
        "The type of the associating resource element."
    ::= { tn3270eResMapEntry 5 }

tn3270eResMapSscpSuppliedName OBJECT-TYPE
    SYNTAX SnaResourceName
--    Rsyntax OCTET STRING(SIZE(0..17))
    ACCESS read-only
    STATUS mandatory
    DESCRIPTION
        "The name of the secondary LU (SLU) as it is known in the
        SNA network.  This name is sent by the SSCP on the
        Activate Logical Unit (ACTLU) request.  The value of this
        object is the empty string if the tn3270eResMapElementName
        is the same as the SSCP-supplied name."
    ::= { tn3270eResMapEntry 6 }

tn3270eTcpConnTable OBJECT-TYPE
    SYNTAX SEQUENCE OF Tn3270eTcpConnEntry
    ACCESS not-accessible
    STATUS mandatory
    DESCRIPTION
        "Provides a table that has an entry for each TN3270(E)
         client connection that is active at a TN3270E server.
         The table was originally modeled after the tcpConnTable
         but was changed to support different client Address types
         and to be indexed first by the remote address and port
         as oppose to local address and port. This is to enable
         use of a SNMP GET-NEXT operation using only the remote
         address and port."
    ::= { tn3270eObjects 9 }

tn3270eTcpConnEntry OBJECT-TYPE
    SYNTAX Tn3270eTcpConnEntry
    ACCESS not-accessible
    STATUS mandatory
    DESCRIPTION
        "Provides in formation about a single TN3270/TN3270E
         session. Note: a tn3270eSrvrConfIndex is not needed
         in this table since the combination of both remote
         local addresses and ports is sufficient to
         guarantee uniqueness between TN3270E Servers on the
         same or actually different hosts."
    INDEX { tn3270eTcpConnRemAddrType, tn3270eTcpConnRemAddress, tn3270eTcpConnRemPort, tn3270eTcpConnLocalAddrType, tn3270eTcpConnLocalAddress, tn3270eTcpConnLocalPort }
    ::= { tn3270eTcpConnTable 1 }

Tn3270eTcpConnEntry ::= SEQUENCE {
    tn3270eTcpConnRemAddrType Tn3270eAddrType,
    tn3270eTcpConnRemAddress Tn3270eTAddress,
    tn3270eTcpConnRemPort UInteger32,
    tn3270eTcpConnLocalAddrType Tn3270eAddrType,
    tn3270eTcpConnLocalAddress Tn3270eTAddress,
    tn3270eTcpConnLocalPort UInteger32,
    tn3270eTcpConnLastActivity TimeTicks,
    tn3270eTcpConnBytesIn Counter32,
    tn3270eTcpConnBytesOut Counter32,
    tn3270eTcpConnResourceElement SnaResourceName,
    tn3270eTcpConnResourceType Tn3270ResourceType,
    tn3270eTcpConnDeviceType Tn3270DeviceTypes,
    tn3270eTcpConnFunctions Tn3270Functions,
    tn3270eTcpConnId UInteger32,
    tn3270eTcpConnClientIdFormat INTEGER,
    tn3270eTcpConnClientId OCTET STRING,
    tn3270eTcpConnMiscInfoFormat OCTET STRING,
    tn3270eTcpConnMiscInfo OCTET STRING,
    tn3270eTcpConnLuLuBindImage OCTET STRING,
    tn3270eTcpConnSnaState INTEGER
    }

tn3270eTcpConnRemAddrType OBJECT-TYPE
    SYNTAX Tn3270eAddrType
--    Rsyntax INTEGER {
--        unknown(0),
--        ipv4(1),
--        ipv6(2)
--        }
    ACCESS not-accessible
    STATUS mandatory
    DESCRIPTION
        "Indicates the type of the value of the
        tn3270eTcpConnRemAddress object. For example,
        ipv4(1) or ipv6(2)."
    ::= { tn3270eTcpConnEntry 1 }

tn3270eTcpConnRemAddress OBJECT-TYPE
    SYNTAX Tn3270eTAddress
--    Rsyntax OCTET STRING(SIZE(0..255))
    ACCESS not-accessible
    STATUS mandatory
    DESCRIPTION
        "The remote address associated with a TN3270E client.
         tn3270eTcpConnRemAddrType indicates the address type
         (ipv4 or ipv6 for example).
        
         If a TN3270(E) client is connected to its
         server via a proxy client the address represented by
         the value of this object should be the remote client's
         address, not the proxy client's address."
    ::= { tn3270eTcpConnEntry 2 }

tn3270eTcpConnRemPort OBJECT-TYPE
    SYNTAX UInteger32(0..65535)
    ACCESS not-accessible
    STATUS mandatory
    DESCRIPTION
        "The remote port associated with a TN3270E client.
        
         If a TN3270(E) client is connected to its
         server via a proxy client the port represented by
         the value of this object should be the remote client's
         port, not the proxy client's port."
    ::= { tn3270eTcpConnEntry 3 }

tn3270eTcpConnLocalAddrType OBJECT-TYPE
    SYNTAX Tn3270eAddrType
--    Rsyntax INTEGER {
--        unknown(0),
--        ipv4(1),
--        ipv6(2)
--        }
    ACCESS not-accessible
    STATUS mandatory
    DESCRIPTION
        "Indicates the type of the value of the
        tn3270eTcpConnLocalAddress object. For example,
        ipv4(1) or ipv6(2)."
    ::= { tn3270eTcpConnEntry 4 }

tn3270eTcpConnLocalAddress OBJECT-TYPE
    SYNTAX Tn3270eTAddress
--    Rsyntax OCTET STRING(SIZE(0..255))
    ACCESS not-accessible
    STATUS mandatory
    DESCRIPTION
        "The local address associated with a TN3270E client.
         tn3270eTcpConnRemAddrType indicates the address type
         (ipv4 or ipv6 for example)."
    ::= { tn3270eTcpConnEntry 5 }

tn3270eTcpConnLocalPort OBJECT-TYPE
    SYNTAX UInteger32(0..65535)
    ACCESS not-accessible
    STATUS mandatory
    DESCRIPTION
        "The remote port associated with a TN3270E client."
    ::= { tn3270eTcpConnEntry 6 }

tn3270eTcpConnLastActivity OBJECT-TYPE
    SYNTAX TimeTicks
    ACCESS read-only
    STATUS mandatory
    DESCRIPTION
        "The number of 100ths of seconds since any data was
         transferred for the associating TCP Connection."
    DEFVAL { 0 }
    ::= { tn3270eTcpConnEntry 7 }

tn3270eTcpConnBytesIn OBJECT-TYPE
    SYNTAX Counter32
--  Units
--    octets
    ACCESS read-only
    STATUS mandatory
    DESCRIPTION
        "The number of bytes received by the server from TCP
         for this connection."
    ::= { tn3270eTcpConnEntry 8 }

tn3270eTcpConnBytesOut OBJECT-TYPE
    SYNTAX Counter32
--  Units
--    octets
    ACCESS read-only
    STATUS mandatory
    DESCRIPTION
        "The number of bytes sent to TCP for this connection."
    ::= { tn3270eTcpConnEntry 9 }

tn3270eTcpConnResourceElement OBJECT-TYPE
    SYNTAX SnaResourceName
--    Rsyntax OCTET STRING(SIZE(0..17))
    ACCESS read-only
    STATUS mandatory
    DESCRIPTION
        "LU/Print secondary name for connecting an client
         into an SNA network."
    ::= { tn3270eTcpConnEntry 10 }

tn3270eTcpConnResourceType OBJECT-TYPE
    SYNTAX Tn3270ResourceType
--    Rsyntax INTEGER {
--        other(0),
--        lu(1),
--        printer(2)
--        }
    ACCESS read-only
    STATUS mandatory
    DESCRIPTION
        "Indicates the type of resource identified by
         tn3270eTcpConnResourceElement."
    ::= { tn3270eTcpConnEntry 11 }

tn3270eTcpConnDeviceType OBJECT-TYPE
    SYNTAX Tn3270DeviceTypes
--    Rsyntax INTEGER {
--        unknown(0),
--        ibm3278d2(1),
--        ibm3278d2E(2),
--        ibm3278d3(3),
--        ibm3278d3E(4),
--        ibm3278d4(5),
--        ibm3278d4E(6),
--        ibm3278d5(7),
--        ibm3278d5E(8),
--        ibmDynamic(9),
--        ibm3287d1(10)
--        }
    ACCESS read-only
    STATUS mandatory
    DESCRIPTION
        "Indicates the device type if negotiated with client.
         This object is also known as logmode."
    ::= { tn3270eTcpConnEntry 12 }

tn3270eTcpConnFunctions OBJECT-TYPE
    SYNTAX Tn3270Functions
--    Rsyntax OCTET STRING(SIZE(2))
    ACCESS read-only
    STATUS mandatory
    DESCRIPTION
        "This object will indicates which of the TN3270 and TN3270E
         functions that are supported by the server was negioted
         with a client. Refer to tn3270eSrvrFunctionsSupported."
    ::= { tn3270eTcpConnEntry 13 }

tn3270eTcpConnId OBJECT-TYPE
    SYNTAX UInteger32
    ACCESS read-only
    STATUS mandatory
    DESCRIPTION
        "The connection identifier associated with a TN3270 or
         a TN3270E session's TCP connection."
    ::= { tn3270eTcpConnEntry 14 }

tn3270eTcpConnClientIdFormat OBJECT-TYPE
    SYNTAX INTEGER {
        unknown(0)
        }
    ACCESS read-only
    STATUS mandatory
    DESCRIPTION
        "The format of the corresponding tn3270eTcpConnClientId
         object:
        
            ENUMERATION    OCTETs  DESCRIPTION
            unknown(0)       0"
    ::= { tn3270eTcpConnEntry 15 }

tn3270eTcpConnClientId OBJECT-TYPE
    SYNTAX OCTET STRING(SIZE(0..512))
    ACCESS read-only
    STATUS mandatory
    DESCRIPTION
        "Additional client identification information whose
         content is defined by the corresponding value of
         tn3270eTcpConnClientIdFormat."
    ::= { tn3270eTcpConnEntry 16 }

tn3270eTcpConnMiscInfoFormat OBJECT-TYPE
    SYNTAX OCTET STRING(SIZE(1))
    ACCESS read-only
    STATUS mandatory
    DESCRIPTION
        "This object defines the content of a corresponding
         tn3270eTcpConnMiscInfo object. This object is defined
         using the BITS SYNTAX in order to enable the presents
         of multiple elements. The order of occurance of the
         selected elements in a tn3270eTcpConnMiscInfo must
         follow the precedence of the associating BIT definition
         with the exception of unknown(1) which must be last
         if selected:
        
         ENUMERATION OCTETs DESCRIPTION
         none(0)       0
         unknown(1)  0..512 A variable length generic field.
         proxyIpv4(2)  4    The actual client is connected
                            via a proxy client whose address
                            is stored in tn3270eTcpConnClientId.
         proxyIpv6(3) 16    The actual client is connected
                            via a proxy client whose address
                            is stored in tn3270eTcpConnClientId.
        
         For example, selection of unknown(1), proxyIpv4(2) and
         proxyIpv6(3) would result in the corresponding
         tn3270eTcpConnMiscInfo containing a proxyIpv6 value
         followed by a proxyIpv4 value and ended with a variable
         length unknown value."
    ::= { tn3270eTcpConnEntry 17 }

tn3270eTcpConnMiscInfo OBJECT-TYPE
    SYNTAX OCTET STRING(SIZE(0..512))
    ACCESS read-only
    STATUS mandatory
    DESCRIPTION
        "Additional client information. The contents of this
         object is defined by the corresponding object
         tn3270eTcpConnMiscInfoFormat."
    ::= { tn3270eTcpConnEntry 18 }

tn3270eTcpConnLuLuBindImage OBJECT-TYPE
    SYNTAX OCTET STRING(SIZE(0..256))
    ACCESS read-only
    STATUS mandatory
    DESCRIPTION
        "When there is a currently active LU-LU session for
        this connection, this object returns the BIND Image
        (defined to be bytes 1-p of the complete BIND Request
        Unit) that was received from the PLU during session
        activation.  When there is no active LU-LU session,
        or when a BIND image is unavailable for some other
        reason, this object returns the empty string."
    ::= { tn3270eTcpConnEntry 19 }

tn3270eTcpConnSnaState OBJECT-TYPE
    SYNTAX INTEGER {
        unknown(0),
        noSluSession(1),
        sscpLuSession(2),
        luLuSession(3)
        }
    ACCESS read-only
    STATUS mandatory
    DESCRIPTION
        "The current state of the SNA side of the end-to-end
        TN3270 connection.  The following states are defined:
        
        unknown(0)          - The true state is not known.
        noSluSession(1)     - The SLU has neither an SSCP-LU
                              nor an LU-LU session active.
        sscpLuSession(2)    - The SSCP-LU session for the SLU
                              is active, but the SLU is not
                              currently in session with a PLU.
        luLuSession(3)      - The SLU currently has an active
                              session with a PLU."
    ::= { tn3270eTcpConnEntry 20 }

tn3270eBasicGroup OBJECT IDENTIFIER ::= { tn3270eGroups 1 }
-- OBJECT-GROUP
--  Status
--    mandatory
--  Descr
--    This group is mandatory for all hosts supporting the
--     TN3270E-MIB.
--  objects
--    tn3270eSrvrConfInactivityTimeout, 
--    tn3270eSrvrConfActivityCheck, tn3270eSrvrConfActivityTimeout, 
--    tn3270eSrvrConfActivityInterval, 
--    tn3270eSrvrFunctionsSupported, tn3270eSrvrConfAdminStatus, 
--    tn3270eSrvrConfOperStatus, tn3270eSrvrConfSessionTermState, 
--    tn3270eSrvrConfSrvrType, tn3270eSrvrConfContact, 
--    tn3270eSrvrConfRowStatus, tn3270eSrvrPortRowStatus, 
--    tn3270eSrvrStatsUpTime, tn3270eSrvrStatsMaxLus, 
--    tn3270eSrvrStatsLusInUse, tn3270eSrvrStatsSpareLus, 
--    tn3270eSrvrStatsMaxPtrs, tn3270eSrvrStatsPtrsInUse, 
--    tn3270eSrvrStatsSparePtrs, tn3270eSrvrStatsConnectsIn, 
--    tn3270eSrvrStatsConnRejects, tn3270eSrvrStatsDisconnects, 
--    tn3270eSrvrStatsOctetsIn, tn3270eSrvrStatsOctetsInLow, 
--    tn3270eSrvrStatsOctetsOut, tn3270eSrvrStatsOctetsOutLow, 
--    tn3270eClientGroupSubnetMask, tn3270eClientGroupPfxLength, 
--    tn3270eClientGroupRowStatus, tn3270eSnaMapLocalName, 
--    tn3270eSnaMapPrimaryLuName

tn3270eSessionGroup OBJECT IDENTIFIER ::= { tn3270eGroups 2 }
-- OBJECT-GROUP
--  Status
--    mandatory
--  Descr
--    This group is mandatory for all hosts supporting the
--     TN3270E-MIB.
--  objects
--    tn3270eResMapAddrType, tn3270eResMapAddress, 
--    tn3270eResMapPort, tn3270eResMapElementType, 
--    tn3270eResMapSscpSuppliedName, tn3270eTcpConnLastActivity, 
--    tn3270eTcpConnBytesIn, tn3270eTcpConnBytesOut, 
--    tn3270eTcpConnResourceElement, tn3270eTcpConnResourceType, 
--    tn3270eTcpConnDeviceType, tn3270eTcpConnFunctions

tn3270eResMapGroup OBJECT IDENTIFIER ::= { tn3270eGroups 3 }
-- OBJECT-GROUP
--  Status
--    mandatory
--  Descr
--    This group is optional for all hosts supporting the
--     TN3270E-MIB.
--  objects
--    tn3270eResPoolElementType, tn3270eResPoolRowStatus, 
--    tn3270eClientResMapRowStatus, tn3270eTcpConnId, 
--    tn3270eTcpConnClientIdFormat, tn3270eTcpConnClientId, 
--    tn3270eTcpConnMiscInfoFormat, tn3270eTcpConnMiscInfo, 
--    tn3270eTcpConnLuLuBindImage, tn3270eTcpConnSnaState

tn3270eCompliance OBJECT IDENTIFIER ::= { tn3270eCompliances 1 }
-- MODULE-COMPLIANCE
--  Status
--    mandatory
--  Descr
--    The compliance statement for agents that support the
--    TN3270E-MIB.
--  Module
--    >>current<<
--   MandGroup
--    tn3270eBasicGroup
--   MandGroup
--    tn3270eSessionGroup
--   OptGroup
--    tn3270eResMapGroup
--   ObjVar
--    tn3270eSrvrConfActivityCheck
--   ObjVar
--    tn3270eSrvrConfActivityTimeout
--   ObjVar
--    tn3270eSrvrConfActivityInterval
--   ObjVar
--    tn3270eSrvrConfAdminStatus


END
