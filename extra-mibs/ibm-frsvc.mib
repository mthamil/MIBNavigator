-- MIB created 5/06/99 21:05:01, by
--   SMIC (the next generation) version 1.6.29, November 22, 1994.

FRAME-RELAY-DTE-SVC-MIB DEFINITIONS ::= BEGIN

-- From file: "frsvc.mi2"
-- Compile options "G A T M"

IMPORTS
    Counter32, Integer32, TimeTicks
            FROM SNMPv2-SMI-v1
    OBJECT-TYPE
            FROM RFC-1212
    TRAP-TYPE
            FROM RFC-1215
    RowStatus, TimeStamp, DisplayString
            FROM SNMPv2-TC-v1
    frame-relay, DLCI
            FROM RFC1315-MIB
    InterfaceIndex
            FROM IF-MIB;

frameRelayDteSvc OBJECT IDENTIFIER ::= { frame-relay 7 }
-- MODULE-IDENTITY
--  LastUpdated
--    9703250910Z
--  OrgName
--    IETF frnetmib Working Group
--  ContactInfo
--    
--              Don Cochrane
--    
--              Cabletron Sys, Inc.
--              35E Industrial Way, 1st Floor
--              Rochester New Hampshire, 03867
--    
--              cochrane@ctron.com 
--  Descr
--     This memo defines a portion of the Management Information Base
--      (MIB) for use with network management protocols in TCP/IP-
--      based internets.  In particular, it defines objects for
--      managing Frame Relay DTE Switched Virtual Circuit's.

frDteSvc        OBJECT IDENTIFIER ::= { frameRelayDteSvc 1 }

frSvcDlcmiTable OBJECT-TYPE
    SYNTAX SEQUENCE OF FrSvcDlcmiEntry
    ACCESS not-accessible
    STATUS mandatory
    DESCRIPTION
        "The Parameters for the Switched Virtual Circuit
        Link Connection Management Interface
        for the frame relay service on this
        interface."
    ::= { frDteSvc 1 }

frSvcDlcmiEntry OBJECT-TYPE
    SYNTAX FrSvcDlcmiEntry
    ACCESS not-accessible
    STATUS mandatory
    DESCRIPTION
        "The information regarding a single switched Data
        Link Connection Management Interface."
    INDEX { frSvcDlcmiIfIndex }
    ::= { frSvcDlcmiTable 1 }

FrSvcDlcmiEntry ::= SEQUENCE {
    frSvcDlcmiIfIndex InterfaceIndex,
    frSvcDlcmiState INTEGER,
    frSvcDlcmiMaxNumCalls Integer32,
    frSvcDlcmiCallSetupTimer Integer32,
    frSvcDlcmiCallProceedingTimer Integer32,
    frSvcDlcmiCallDisconnectTimer Integer32,
    frSvcDlcmiCallReleaseTimer Integer32,
    frSvcDlcmiStatusEnquiryTimer Integer32,
    frSvcDlcmiErrorThreshold Integer32,
    frSvcDlcmiResetSentTimer Integer32,
    frSvcDlcmiResetAckTimer Integer32,
    frSvcDlcmiIdleTimer Integer32,
    frSvcDlcmiRetransmissionTimer TimeTicks,
    frSvcDlcmiNumRetransmissions Integer32,
    frSvcDlcmiMaxInfoFieldSize Integer32,
    frSvcDlcmiMaxInfoFrames Integer32,
    frSvcDlcmiQ922State INTEGER
    }

frSvcDlcmiIfIndex OBJECT-TYPE
    SYNTAX InterfaceIndex
--    Rsyntax Integer32
    ACCESS read-only
    STATUS mandatory
    DESCRIPTION
        "The ifIndex value of the corresponding ifEntry."
    ::= { frSvcDlcmiEntry 1 }

frSvcDlcmiState OBJECT-TYPE
    SYNTAX INTEGER {
        q933SVC(1),
        x36(2),
        none(3)
        }
    ACCESS read-write
    STATUS mandatory
    DESCRIPTION
        "This variable states which Data Link Connection
        Management scheme is on the Frame Relay
        switched interface."
    ::= { frSvcDlcmiEntry 2 }

frSvcDlcmiMaxNumCalls OBJECT-TYPE
    SYNTAX Integer32
    ACCESS read-only
    STATUS mandatory
    DESCRIPTION
        "Indicates the maximum number of calls
        allowed on the interface."
    ::= { frSvcDlcmiEntry 3 }

frSvcDlcmiCallSetupTimer OBJECT-TYPE
    SYNTAX Integer32
--  Units
--    seconds
    ACCESS read-write
    STATUS mandatory
    DESCRIPTION
        "This timer is started when the CALL SETUP
        message is sent. The timer is stopped when
        the sender receives a CALL PROCEEDING
        message. If the timer, expressed in
        seconds, expires, it is retried
        once before the call is cleared.
        The default value is 4 seconds."
    REFERENCE
        "ITU-T Standard Q.931,
        Section 9.2: Timer T303."
    DEFVAL { 4 }
    ::= { frSvcDlcmiEntry 4 }

frSvcDlcmiCallProceedingTimer OBJECT-TYPE
    SYNTAX Integer32
--  Units
--    seconds
    ACCESS read-write
    STATUS mandatory
    DESCRIPTION
        "This timer is started when the CALL
        PROCEEDING message is sent. The timer
        is stopped when the sender
        receives a CALL CONNECT message. If
        the timer, expressed in seconds,
        expires, the call is cleared.
        The default value is 10 seconds."
    REFERENCE
        "ITU-T Standard Q.931,
        Section 9.2: Timer T310."
    DEFVAL { 10 }
    ::= { frSvcDlcmiEntry 5 }

frSvcDlcmiCallDisconnectTimer OBJECT-TYPE
    SYNTAX Integer32
--  Units
--    seconds
    ACCESS read-write
    STATUS mandatory
    DESCRIPTION
        "This timer is started when the
        DISCONNECT message is sent. The timer
        is stopped when the sender
        receives a RELEASE message. The sender
        then responds with a RELEASE COMPLETE
        message. If the timer, expressed in
        seconds, expires, the sender starts
        up Timer T308, and sends a RELEASE
        message. The default value for this timer is 30
        seconds."
    REFERENCE
        "ITU-T Standard Q.931,
        Section 9.2: Timer T305."
    DEFVAL { 30 }
    ::= { frSvcDlcmiEntry 6 }

frSvcDlcmiCallReleaseTimer OBJECT-TYPE
    SYNTAX Integer32
--  Units
--    seconds
    ACCESS read-write
    STATUS mandatory
    DESCRIPTION
        "This timer is started if timer
        T305 expires. This timer
        is stopped when the sender
        receives a RELEASE message. If
        the timer, expressed in seconds,
        expires, the timer sequence is
        reinitiated. If the timer
        expires a second time the call is
        cleared. The default value fo rthis timer
        is 4 seconds."
    REFERENCE
        "ITU-T Standard Q.931,
        Section 9.2: Timer T308."
    DEFVAL { 4 }
    ::= { frSvcDlcmiEntry 7 }

frSvcDlcmiStatusEnquiryTimer OBJECT-TYPE
    SYNTAX Integer32
--  Units
--    seconds
    ACCESS read-write
    STATUS mandatory
    DESCRIPTION
        "This timer is started when a STATUS
        ENQUIRY message is sent. If a STATUS
        message is received, the timer will be
        stopped. If the Timer expires it may be
        retried an implementation specific number
        (n) of times. Upon expiry of (n), the
        call is cleared. The default value is 4 retries."
    REFERENCE
        "ITU-T Standard Q.931,
        Section 9.2: Timer T322."
    DEFVAL { 4 }
    ::= { frSvcDlcmiEntry 8 }

frSvcDlcmiErrorThreshold OBJECT-TYPE
    SYNTAX Integer32
    ACCESS read-write
    STATUS mandatory
    DESCRIPTION
        "This is the implementation specific
        number of times that the STATUS
        ENQUIRY Timer, T322, will be retried."
    REFERENCE
        "ITU-T Standard Q.931, Section 9.2."
    ::= { frSvcDlcmiEntry 9 }

frSvcDlcmiResetSentTimer OBJECT-TYPE
    SYNTAX Integer32
--  Units
--    seconds
    ACCESS read-write
    STATUS mandatory
    DESCRIPTION
        "This timer is started when a RESTART
        message is sent. If a RESTART
        ACKNOWLEDGEmessage is received,
        the timer will be stopped. If the Timer expires
        expires it may be retried one or more times
        until a RESTART ACKNOWLEDGE message
        is returned. Meanwhile No calls shall be
        placed or accepted over the interface by
        the originator of the RESTART message.
        The network shall limit the number of
        consecutive unsuccessful attempts to a
        default of 2. The default value for the
        Timer is 120 seconds"
    REFERENCE
        "ITU-T Standard Q.931,
        Section 9.2: Timer T316."
    DEFVAL { 120 }
    ::= { frSvcDlcmiEntry 10 }

frSvcDlcmiResetAckTimer OBJECT-TYPE
    SYNTAX Integer32
--  Units
--    seconds
    ACCESS read-write
    STATUS mandatory
    DESCRIPTION
        "This timer is started when a RESTART
        message is received. At this time the
        receiving entity shall initiate the
        appropriate internal actions to return
        the specified interface to the idle
        condition and call references to the
        Null state. Upon expiry of the timer,
        a notification shall be made to the
        maintenance entity. NOTE: This Timer
        MUST be less than Timer T316. "
    REFERENCE
        "ITU-T Standard Q.931,
        Section 9.2: Timer T317."
    ::= { frSvcDlcmiEntry 11 }

frSvcDlcmiIdleTimer OBJECT-TYPE
    SYNTAX Integer32
--  Units
--    seconds
    ACCESS read-write
    STATUS mandatory
    DESCRIPTION
        "This is the maximum time allowed
        without any frames being exchanged.
        The default for this timer is 30 seconds."
    REFERENCE
        "ITU-T Standard Q.921,
        Section 5.9 / Q.922 Section
        5.9: Timer T203."
    DEFVAL { 30 }
    ::= { frSvcDlcmiEntry 12 }

frSvcDlcmiRetransmissionTimer OBJECT-TYPE
    SYNTAX TimeTicks
    ACCESS read-write
    STATUS mandatory
    DESCRIPTION
        "This is the re-transmission timer.
        It is started upon transmission of
        frames. When a response is received,
        the timer will be shut down. If the
        timer expires , it may be retried N200
        times. When N200 times have been
        reached, a DL-RELEASE message will
        be sent to the Layer 3 entity. The default
        for this timer is 1.5 seconds."
    REFERENCE
        "ITU-T Standard Q.921,
        Section 5.9 / Q.922 Section
        5.9: Timer T200."
    DEFVAL { 1500 }
    ::= { frSvcDlcmiEntry 13 }

frSvcDlcmiNumRetransmissions OBJECT-TYPE
    SYNTAX Integer32
    ACCESS read-write
    STATUS mandatory
    DESCRIPTION
        "This value indicates the number of
        times T200 timer will be retried.
        When N200 times have been reached,
        a DL-RELEASE message will be sent
        to the Layer 3 entity. The default for this
        value is 3 retries."
    REFERENCE
        "ITU-T Standard Q.921,
        Section 5.9 / Q.922 Section
        5.9: N200."
    DEFVAL { 3 }
    ::= { frSvcDlcmiEntry 14 }

frSvcDlcmiMaxInfoFieldSize OBJECT-TYPE
    SYNTAX Integer32
--  Units
--    octets
    ACCESS read-write
    STATUS mandatory
    DESCRIPTION
        "This value indicates the maximum
        number of octets in an Information field.
        The default value is 260 octets."
    REFERENCE
        "ITU-T Standard Q.921,
        Section 5.9 / Q.922 Section
        5.9: N201."
    DEFVAL { 260 }
    ::= { frSvcDlcmiEntry 15 }

frSvcDlcmiMaxInfoFrames OBJECT-TYPE
    SYNTAX Integer32(1..127)
    ACCESS read-write
    STATUS mandatory
    DESCRIPTION
        "This value indicates the maximum
        number of sequentially numbered I
        frames that may be outstanding
        (that is, unacknowledged) at any
        given time. This number shall not
        exceed 127. For a 16Kbps link: k =
        3, 64Kbps: k = 7 (this is the default value),
        384Kbps: k = 32, 1.5Mbps/1.92Mbps: k = 40."
    REFERENCE
        "ITU-T Standard Q.921,
        Section 5.9 / Q.922 Section
        5.9: k."
    DEFVAL { 7 }
    ::= { frSvcDlcmiEntry 16 }

frSvcDlcmiQ922State OBJECT-TYPE
    SYNTAX INTEGER {
        teiUnassigned(1),
        assignAwaitingTei(2),
        establishingAwaitingTei(3),
        teiAssigned(4),
        awaitingEstablishment(5),
        awaitingRelease(6),
        multipleFrameEstablished(7),
        timerRecovery(8)
        }
    ACCESS read-only
    STATUS mandatory
    DESCRIPTION
        "This value indicates the state of the
        Q.922 Point to Point Data Link Layer
        Negotiation. "
    REFERENCE
        "ITU-T Standard Q.922,
        Appendix B.2"
    ::= { frSvcDlcmiEntry 17 }

frSvcTable OBJECT-TYPE
    SYNTAX SEQUENCE OF FrSvcEntry
    ACCESS not-accessible
    STATUS mandatory
    DESCRIPTION
        "A table containing information about specific Data
        Link Connection Identifiers and corresponding switched
        virtual circuits."
    ::= { frDteSvc 2 }

frSvcEntry OBJECT-TYPE
    SYNTAX FrSvcEntry
    ACCESS not-accessible
    STATUS mandatory
    DESCRIPTION
        "The information regarding a single  switched Data
        Link Connection Identifier."
    INDEX { frSvcIfIndex, frSvcDlci }
    ::= { frSvcTable 1 }

FrSvcEntry ::= SEQUENCE {
    frSvcIfIndex InterfaceIndex,
    frSvcDlci DLCI,
    frSvcReceivedFECNs Counter32,
    frSvcReceivedBECNs Counter32,
    frSvcSentFrames Counter32,
    frSvcSentOctets Counter32,
    frSvcReceivedFrames Counter32,
    frSvcReceivedOctets Counter32,
    frSvcCreationTime TimeTicks,
    frSvcInMaxFmifSize Integer32,
    frSvcOutMaxFmifSize Integer32,
    frSvcInCommittedBurst Integer32,
    frSvcOutCommittedBurst Integer32,
    frSvcInExcessBurst Integer32,
    frSvcOutExcessBurst Integer32,
    frSvcInCIR Integer32,
    frSvcOutCIR Integer32,
    frSvcInMinCIR Integer32,
    frSvcOutMinCIR Integer32,
    frSvcState INTEGER,
    frSvcCallReferenceValue Integer32,
    frSvcCallingAddr DisplayString,
    frSvcCallingSubAddr DisplayString,
    frSvcCalledAddr DisplayString,
    frSvcCalledSubAddr DisplayString,
    frSvcCallSetup INTEGER,
    frSvcCallOrigination INTEGER
    }

frSvcIfIndex OBJECT-TYPE
    SYNTAX InterfaceIndex
--    Rsyntax Integer32
    ACCESS read-only
    STATUS mandatory
    DESCRIPTION
        "The ifIndex Value of the ifEntry this  virtual
        circuit is layered onto."
    ::= { frSvcEntry 1 }

frSvcDlci OBJECT-TYPE
    SYNTAX DLCI
--    Rsyntax INTEGER
    ACCESS read-only
    STATUS mandatory
    DESCRIPTION
        "The Data Link Connection Identifier  for  this
        virtual circuit."
    ::= { frSvcEntry 2 }

frSvcReceivedFECNs OBJECT-TYPE
    SYNTAX Counter32
    ACCESS read-only
    STATUS mandatory
    DESCRIPTION
        "Number of frames received from the network in-
        dicating  forward  congestion since the virtual
        circuit was created."
    REFERENCE
        "Draft American National  Standard  T1.618-1991,
        Section 3.3.3"
    ::= { frSvcEntry 3 }

frSvcReceivedBECNs OBJECT-TYPE
    SYNTAX Counter32
    ACCESS read-only
    STATUS mandatory
    DESCRIPTION
        "Number of frames received from the network in-
        dicating  backward congestion since the virtual
        circuit was created."
    REFERENCE
        "Draft American National  Standard  T1.618-1991,
        Section 3.3.4"
    ::= { frSvcEntry 4 }

frSvcSentFrames OBJECT-TYPE
    SYNTAX Counter32
    ACCESS read-only
    STATUS mandatory
    DESCRIPTION
        "The number of frames sent  from  this  virtual
        circuit since it was created."
    ::= { frSvcEntry 5 }

frSvcSentOctets OBJECT-TYPE
    SYNTAX Counter32
--  Units
--    octets
    ACCESS read-only
    STATUS mandatory
    DESCRIPTION
        "The number of octets sent  from  this  virtual
        circuit since it was created."
    ::= { frSvcEntry 6 }

frSvcReceivedFrames OBJECT-TYPE
    SYNTAX Counter32
    ACCESS read-only
    STATUS mandatory
    DESCRIPTION
        "Number of frames received  over  this  virtual
        circuit since it was created."
    ::= { frSvcEntry 7 }

frSvcReceivedOctets OBJECT-TYPE
    SYNTAX Counter32
--  Units
--    octets
    ACCESS read-only
    STATUS mandatory
    DESCRIPTION
        "Number of octets received  over  this  virtual
        circuit since it was created."
    ::= { frSvcEntry 8 }

frSvcCreationTime OBJECT-TYPE
    SYNTAX TimeTicks
    ACCESS read-only
    STATUS mandatory
    DESCRIPTION
        "The value of sysUpTime when the  virtual  cir-
        cuit was created."
    ::= { frSvcEntry 9 }

frSvcInMaxFmifSize OBJECT-TYPE
    SYNTAX Integer32
--  Units
--    octets
    ACCESS read-write
    STATUS mandatory
    DESCRIPTION
        "This variable indicates the maximum amount  of
        end user data octets in a frame for in the direction
        of the calling user to the called user. The default
        value is 262 octets."
    REFERENCE
        "ITU-T Standard Q.933,
        Section 4.5.19"
    DEFVAL { 262 }
    ::= { frSvcEntry 10 }

frSvcOutMaxFmifSize OBJECT-TYPE
    SYNTAX Integer32
--  Units
--    octets
    ACCESS read-write
    STATUS mandatory
    DESCRIPTION
        "This variable indicates the maximum amount  of
        end user data octets in a frame for in the direction
        of the called user to the calling user. The default
        value is 262 octets."
    REFERENCE
        "ITU-T Standard Q.933,
        Section 4.5.19"
    DEFVAL { 262 }
    ::= { frSvcEntry 11 }

frSvcInCommittedBurst OBJECT-TYPE
    SYNTAX Integer32
--  Units
--    bits
    ACCESS read-write
    STATUS mandatory
    DESCRIPTION
        "This variable indicates the maximum amount  of
        data,  in  bits,  that  the  network  agrees to
        accept under normal  conditions,  during  the
        measurement interval. The default value is 0."
    REFERENCE
        "ITU-T Standard Q.933,
        Section 4.5.19"
    DEFVAL { 0 }
    ::= { frSvcEntry 12 }

frSvcOutCommittedBurst OBJECT-TYPE
    SYNTAX Integer32
--  Units
--    bits
    ACCESS read-write
    STATUS mandatory
    DESCRIPTION
        "This variable indicates the maximum amount  of
        data,  in  bits,  that  the  network  agrees to
        transfer under normal  conditions,  during  the
        measurement interval. The default value is 0."
    REFERENCE
        "ITU-T Standard Q.933,
        Section 4.5.19"
    DEFVAL { 0 }
    ::= { frSvcEntry 13 }

frSvcInExcessBurst OBJECT-TYPE
    SYNTAX Integer32
--  Units
--    bits
    ACCESS read-write
    STATUS mandatory
    DESCRIPTION
        "This variable indicates the maximum amount  of
        uncommitted data bits that the network will at-
        tempt to receive over the measurement interval.
        By default, if not configured when creating the
        entry, the Excess Information Burst Size is set
        to the value of ifSpeed."
    REFERENCE
        "ITU-T Standard Q.933,
        Section 4.5.19"
    ::= { frSvcEntry 14 }

frSvcOutExcessBurst OBJECT-TYPE
    SYNTAX Integer32
--  Units
--    bits
    ACCESS read-write
    STATUS mandatory
    DESCRIPTION
        "This variable indicates the maximum amount  of
        uncommitted data bits that the network will at-
        tempt to deliver over the measurement interval.
        By default, if not configured when creating the
        entry, the Excess Information Burst Size is set
        to the value of ifSpeed."
    REFERENCE
        "ITU-T Standard Q.933,
        Section 4.5.19"
    ::= { frSvcEntry 15 }

frSvcInCIR OBJECT-TYPE
    SYNTAX Integer32
--  Units
--    bits per second
    ACCESS read-write
    STATUS mandatory
    DESCRIPTION
        "CIR is the average number of 'Frame Re-
        lay  Information  Field'  bits  received per
        second across a user network interface  to the
        calling user, measured over the measurement inter-
        val. The default value is 0."
    REFERENCE
        "ITU-T Standard Q.933,
        Section 4.5.19"
    DEFVAL { 0 }
    ::= { frSvcEntry 16 }

frSvcOutCIR OBJECT-TYPE
    SYNTAX Integer32
--  Units
--    bits per second
    ACCESS read-write
    STATUS mandatory
    DESCRIPTION
        "CIR is the average number of 'Frame Re-
        lay  Information  Field'  bits  transferred per
        second across a user network interface  from the
        calling user, measured over the measurement inter-
        val. The default value is 0."
    REFERENCE
        "ITU-T Standard Q.933,
        Section 4.5.19"
    DEFVAL { 0 }
    ::= { frSvcEntry 17 }

frSvcInMinCIR OBJECT-TYPE
    SYNTAX Integer32
--  Units
--    bits per second
    ACCESS read-write
    STATUS mandatory
    DESCRIPTION
        "Minimum Acceptable CIR is the lowest
        throughput value, in the direction to the
        calling user, expressed in bits per second,
        that the calling user is willing to accept for
        the call. If the network or the called user is
        unable to support this throughput, the call
        will be cleared. The default value is 0."
    REFERENCE
        "ITU-T Standard Q.933,
        Section 4.5.19"
    DEFVAL { 0 }
    ::= { frSvcEntry 18 }

frSvcOutMinCIR OBJECT-TYPE
    SYNTAX Integer32
--  Units
--    bits per second
    ACCESS read-write
    STATUS mandatory
    DESCRIPTION
        "Minimum Acceptable CIR is the lowest
        throughput value, in the direction from the
        calling user, expressed in bits per second,
        that the calling user is willing to accept for
        the call. If the network or the called user is
        unable to support this throughput, the call
        will be cleared. The default value is 0."
    REFERENCE
        "ITU-T Standard Q.933,
        Section 4.5.19"
    DEFVAL { 0 }
    ::= { frSvcEntry 19 }

frSvcState OBJECT-TYPE
    SYNTAX INTEGER {
        inProcess(1),
        complete(2)
        }
    ACCESS read-only
    STATUS mandatory
    DESCRIPTION
        "Indicates whether the Connection has
        been completed and data can proceed (2),
        or if the call setup is still in process (1)."
    ::= { frSvcEntry 20 }

frSvcCallReferenceValue OBJECT-TYPE
    SYNTAX Integer32
    ACCESS read-only
    STATUS mandatory
    DESCRIPTION
        "Indicates the call identity number of the call
        on the interface."
    REFERENCE
        "ITU-T Standard Q.931,
        Section 4.5.6"
    ::= { frSvcEntry 21 }

frSvcCallingAddr OBJECT-TYPE
    SYNTAX DisplayString
--    Rsyntax OCTET STRING(SIZE(0..255))
    ACCESS read-write
    STATUS mandatory
    DESCRIPTION
        "Indicates the address of the calling
        party."
    REFERENCE
        "ITU-T Standard Q.931,
        Section 4.5.9"
    ::= { frSvcEntry 22 }

frSvcCallingSubAddr OBJECT-TYPE
    SYNTAX DisplayString
--    Rsyntax OCTET STRING(SIZE(0..255))
    ACCESS read-write
    STATUS mandatory
    DESCRIPTION
        "Indicates the sub-address of the
        calling party."
    REFERENCE
        "ITU-T Standard Q.931,
        Section 4.5.10"
    ::= { frSvcEntry 23 }

frSvcCalledAddr OBJECT-TYPE
    SYNTAX DisplayString
--    Rsyntax OCTET STRING(SIZE(0..255))
    ACCESS read-write
    STATUS mandatory
    DESCRIPTION
        "Indicates the address of the called
        party."
    REFERENCE
        "ITU-T Standard Q.931,
        Section 4.5.7"
    ::= { frSvcEntry 24 }

frSvcCalledSubAddr OBJECT-TYPE
    SYNTAX DisplayString
--    Rsyntax OCTET STRING(SIZE(0..255))
    ACCESS read-write
    STATUS mandatory
    DESCRIPTION
        "Indicates the sub-address of the
        called party."
    REFERENCE
        "ITU-T Standard Q.931,
        Section 4.5.8"
    ::= { frSvcEntry 25 }

frSvcCallSetup OBJECT-TYPE
    SYNTAX INTEGER {
        setup(1),
        disconnect(2)
        }
    ACCESS read-write
    STATUS mandatory
    DESCRIPTION
        "Indicates whether the call should
        be Setup or Disconnected."
    ::= { frSvcEntry 26 }

frSvcCallOrigination OBJECT-TYPE
    SYNTAX INTEGER {
        remote(1),
        local(2)
        }
    ACCESS read-only
    STATUS mandatory
    DESCRIPTION
        "Indicates the direction of the call.
        identifies the circuit as the calling
        (local) or the called side (remote)."
    REFERENCE
        "ITU-T Standard Q.931,
        Section 4.5.9"
    ::= { frSvcEntry 27 }


END
