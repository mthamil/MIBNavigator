---------------------------------------------------------------------          
 --                                                                             
 -- April 9, 1997 - Version 1.1.0                                               
 --                                                                             
 -- Ken White,   IBM vnet:      kwhite at ralvm12                               
 --              Internet:      kennethw@vnet.ibm.com                           
 --    IBM TCP/IP MVS Development                                               
 --    Research Triangle Park, NC                                               
 --                                                                             
 -- Replace   IBMTCPIPMVS                                                       
 --           ibmTcpIpMvs                                                       
 --                                                                             
 -- Program name : IBM TCP/IP MVS Enterprise Specific MIB                       
 --                ASN.1 Description file                                       
 -- Requires: TCP/IP for MVS Restructure                                        
 -- Description : Managing the IBM TCP/IP MVS private MIB                       
 --                                                                             
 ---------------------------------------------------------------------          
 IBMTCPIPMVS-MIB DEFINITIONS ::= BEGIN                                          
                                                                                
        IMPORTS                                                                 
            MODULE-IDENTITY, OBJECT-TYPE, NOTIFICATION-TYPE,                    
            enterprises, Integer32, IpAddress, TimeTicks, Counter32             
               FROM SNMPv2-SMI                  -- RFC1902                      
                                                                                
            TEXTUAL-CONVENTION, DisplayString, DateAndTime                      
               FROM SNMPv2-TC                   -- RFC1903                      
                                                                                
           MODULE-COMPLIANCE, OBJECT-GROUP, NOTIFICATION-GROUP                  
              FROM SNMPv2-CONF                 -- RFC1904                       
                                                                                
           ifIndex                                                              
              FROM IF-MIB                                                       
                                                                                
           ipForwardEntry                                                       
              FROM IP-FORWARD-MIB                                               
                                                                                
           tcpConnEntry, udpEntry                                               
              FROM RFC1213-MIB;                                                 
                                                                                
--                                                                              
--      mvsSNMPagent OID mappings                                               
--                                                                              
--      mvsSNMPagent ::= { 1.3.6.1.4.1.2.6.19 }                                 
--      mvsSNMPRemPing ::= { mvsSNMPagent 1 } <- obsolete                       
--      ibmTCPIPmvsMIB ::= { mvsSNMPagent 2 }                                   
--         ibmRemotePingGroup ::= { ibmTCPIPmvsMIBObjects 1 }                   
--         ibmTcpipMvsSystem ::= { ibmTCPIPmvsMIBObjects 2 }                    
--         ibmTcpipMvsInterfaceGroup ::= { ibmTCPIPmvsMIBObjects 3 }            
--         ibmTcpipMvsPortGroup ::= { ibmTCPIPmvsMIBObjects 4 }                 
--         ibmTcpipMvsRouteGroup ::= { ibmTCPIPmvsMIBObjects 5 }                
--         ibmTcpipMvsAtmGroup ::= { ibmTCPIPmvsMIBObjects 6 }                  
--         ibmTcpipMvsTcpGroup ::= { ibmTCPIPmvsMIBObjects 7 }                  
--         ibmTcpipMvsUdpGroup ::= { ibmTCPIPmvsMIBObjects 8 }                  
--                                                                              
--      SNMPv2 Agent's sysObjectId                                              
--         ibmTcpIpMvs ::= { 1.3.6.1.4.1.2.3.13 }                               
--      SNMPv2 Agent's sysORTable entry                                         
--           ::= { 1.3.6.1.4.1.2.11.7.1 }                                       
--      DPI Subagent OID used with DPI and placed in sysORTable                 
--         ibmTcpIpMvsDpiSaCaps ::= { 1.3.6.1.4.1.2.11.7.2 }                    
--                                                                              
                                                                                
        ibmTCPIPmvsMIB MODULE-IDENTITY                                          
           LAST-UPDATED "9710240000Z"                                           
           ORGANIZATION "IBM TCP/IP MVS Development"                            
           CONTACT-INFO                                                         
               "        Kenneth White                                           
                                                                                
                Postal: International Business Machines Corporation             
                        P.O. Box 12195                                          
                        Dept. G80/Bldg. 503                                     
                        Research Triangle Park, NC 27709                        
                        USA                                                     
                                                                                
                   Tel: +1 919 254 0102                                         
                   Fax: +1 919 254 4027                                         
                                                                                
                E-mail: kennethw@vnet.ibm.com"                                  
           DESCRIPTION                                                          
               "The IBM TCP/IP for MVS Enterprise Specific                      
                MIB definitions for enabling management of                      
                a TCP/IP for MVS system."                                       
        ::= { mvsSNMPagent 2 }                                                  
                                                                                
                                                                                
        ibm OBJECT IDENTIFIER ::= { enterprises 2 }                             
        ibmProd OBJECT IDENTIFIER ::= { ibm 6 }                                 
        mvsSNMPagent OBJECT IDENTIFIER ::= { ibmProd 19 }                       
        ibmAgents OBJECT IDENTIFIER ::= { ibm 10 }                              
        ibmAgentCapabilities OBJECT IDENTIFIER ::= { ibm 11 }                   
                                                                                
                                                                                
 ibmTCPIPmvsMIBTraps     OBJECT IDENTIFIER ::= { ibmTCPIPmvsMIB 0 }             
 ibmTCPIPmvsAdmin        OBJECT IDENTIFIER ::= { ibmTCPIPmvsMIB 1 }             
 ibmTCPIPmvsMIBObjects   OBJECT IDENTIFIER ::= { ibmTCPIPmvsMIB 2 }             
 ibmTCPIPmvsConformance  OBJECT IDENTIFIER ::= { ibmTCPIPmvsMIB 3 }             
                                                                                
 ---------------------------------------------------------------------          
 -- Textual Conventions                                                         
 ---------------------------------------------------------------------          
                                                                                
     TypeOfService ::= TEXTUAL-CONVENTION                                       
          DISPLAY-HINT "1a"                                                     
          STATUS       current                                                  
          DESCRIPTION                                                           
           "Definition of Type-of-Service (tos). The TOS facility is            
            one of the features of the Type of Service octet in the             
            IP datagram header.  The Type of Service octet consists             
            of three fields:                                                    
                                                                                
                 0     1     2     3     4     5     6     7                    
              +-----+-----+-----+-----+-----+-----+-----+-----+                 
              :                 :                       :     :                 
              :   PRECEDENCE    :          TOS          : MBZ :                 
              :                 :                       :     :                 
              +-----+-----+-----+-----+-----+-----+-----+-----+                 
                                                                                
            The first field, labeled 'PRECEDENCE' above, is intended            
            to denote the importance or priority of the datagram.               
            The second field, labeled 'TOS' above, denotes how the              
            network should make tradeoffs between throughput, delay,            
            reliability, and cost.                                              
                                                                                
            The last field, labeled 'MBZ' (for 'must be zero') above,           
            is currently unused.  The originator of a datagram sets             
            this field zero (unless participating in an Internet                
            protocol experiment which makes use of that bit).  Routers          
            and recipients of datagrams ignore the value of this field.         
            This field is copied fragmentation.                                 
                                                                                
            In the past there has been some confusion about the size            
            of the TOS field.  RFC-791 defined it as a three bit field,         
            including bits 3-5 in the figure above.  It included bit 6          
            in the MBZ field.  RFC-1122 added bits 6 and 7 to the TOS           
            field, eliminating the MBZ field.  RFC-1349 further                 
            redefined the TOS field to be the four bits shown in the            
            figure above.                                                       
                                                                                
            The semantics of the following TOS field values (expressed          
            as binary numbers):                                                 
                                                                                
               1000   --   minimize delay                                       
               0100   --   maximize throughput                                  
               0010   --   maximize reliability                                 
               0001   --   minimize monetary cost                               
               0000   --   normal service                                       
                                                                                
            Precendence declarations                                            
                                                                                
                111   --    network control                                     
                110   --    internetwork control                                
                101   --    critic ECP                                          
                100   --    flash override                                      
                011   --    flash                                               
                010   --    immediate                                           
                001   --    priority                                            
                000   --    routine                                             
                                                                                
            TOS default is 0."                                                  
          SYNTAX       Integer32                                                
-- OCTET STRING (SIZE(1))                                                       
                                                                                
     DeviceLinkTypes ::= TEXTUAL-CONVENTION                                     
          DISPLAY-HINT "1a"                                                     
          STATUS       current                                                  
          DESCRIPTION                                                           
           "Defines the various device and link types."                         
          SYNTAX  INTEGER {                                                     
                             unknown(0),                                        
                             lcs(1),                                            
                             ctc(2),                                            
                             claw(3),                                           
                             cdlc(4),                                           
                             atm(5),                                            
                             x25npsi(6),                                        
                             vipa(7),                                           
                             loopback(8),                                       
                             hch(9),                                            
                             ethernet(10),                                      
                             t8023(11),                                         
                             etheror8023(12),                                   
                             ibmtr(13),                                         
                             fddi(14),                                          
                             ip(15),                                            
                             iucv(16),                                          
                             stack(17),                                         
                             mpcptp(18),                                        
                             snalu0(19),                                        
                             snalu62(20)                                        
                           }                                                    
                                                                                
 ---------------------------------------------------------------------          
 -- Define the groups of objects within the MIBObjects subtree                  
 ---------------------------------------------------------------------          
                                                                                
 ibmRemotePingGroup OBJECT IDENTIFIER ::= { ibmTCPIPmvsMIBObjects 1 }           
 -- This group of objects provides the remote ping function for                 
 -- All TCP/IP for MVS releases from V3R3 and up.                               
                                                                                
 ibmTcpipMvsSystem OBJECT IDENTIFIER                                            
          ::= { ibmTCPIPmvsMIBObjects 2 }                                       
 -- This group defines various TCP/IP for MVS global controls or                
 -- system parameters/settings.                                                 
                                                                                
 ibmTcpipMvsInterfaceGroup OBJECT IDENTIFIER                                    
          ::= { ibmTCPIPmvsMIBObjects 3 }                                       
                                                                                
 ibmTcpipMvsPortGroup OBJECT IDENTIFIER                                         
          ::= { ibmTCPIPmvsMIBObjects 4 }                                       
                                                                                
 ibmTcpipMvsRouteGroup OBJECT IDENTIFIER                                        
          ::= { ibmTCPIPmvsMIBObjects 5 }                                       
                                                                                
 ibmTcpipMvsAtmGroup OBJECT IDENTIFIER                                          
          ::= { ibmTCPIPmvsMIBObjects 6 }                                       
                                                                                
 ibmTcpipMvsTcpGroup OBJECT IDENTIFIER                                          
          ::= { ibmTCPIPmvsMIBObjects 7 }                                       
                                                                                
 ibmTcpipMvsUdpGroup OBJECT IDENTIFIER                                          
          ::= { ibmTCPIPmvsMIBObjects 8 }                                       
                                                                                
                                                                                
 --                                                                             
 --     This object is obsolete, don't use it!                                  
 --                                                                             
        ibmSNMPRemPing OBJECT-TYPE                                              
           SYNTAX  Integer32                                                    
           MAX-ACCESS  read-only                                                
           STATUS  obsolete                                                     
           DESCRIPTION                                                          
                 "The number of milliseconds it takes for an icmp               
                  echo request to respond.  ibmSNMPRemPing is -1 if             
                  there is an internal error, -2 if the echo request            
                  timed out, -4 if the packet size is invalid,                  
                  -5 if the timeout is invalid, -6 if                           
                  the IP address was not valid and -7 if the                    
                  format of the MIB instance is not valid.                      
                    To request the icmp response time for ip                    
                  address a.b.c.d with a timeout of e and a packet              
                  size of f, send an snmp get request for                       
                  ibmSNMPRemPing.f.e.a.b.c.d.  For example,                     
                  suppose one wanted to find out the number of                  
                  milliseconds it took to ping address 9.67.30.4,               
                  with a timeout of 8 seconds, and a packet size of             
                  94 bytes.  Accordingly,                                       
                  ibmSNMPRemPing.94.8.9.67.30.4 would identify the              
                  number of milliseconds."                                      
        REFERENCE                                                               
                 "Refer to the IBM TCP/IP for MVS User's                        
                  Guide (SC31-7136-00) for an explanation of the                
                  remote ping function."                                        
        ::= { mvsSNMPagent 1 }                                                  
                                                                                
 ---------------------------------------------------------------------          
 -- ibmRemotePingGroup                                                          
 ---------------------------------------------------------------------          
                                                                                
        --                                                                      
        -- Definition of the remote ping table for use in requesting            
        -- the ping time between two TCP/IP hosts.                              
        --                                                                      
        ibmRemotePingTable OBJECT-TYPE                                          
        SYNTAX SEQUENCE OF IbmRemotePingEntry                                   
        MAX-ACCESS not-accessible                                               
        STATUS current                                                          
        DESCRIPTION                                                             
           "Defines the a remote ping table in order to use                     
            the various parameters as indeces into the table."                  
        ::= { ibmRemotePingGroup 1 }                                            
                                                                                
        ibmRemotePingEntry OBJECT-TYPE                                          
        SYNTAX IbmRemotePingEntry                                               
        MAX-ACCESS not-accessible                                               
        STATUS current                                                          
        DESCRIPTION                                                             
           "Defines an entry in the ibmRemotePingTable. This table              
            does not actual exist, but is used to faciliate passing             
            the remote ping parameters."                                        
        INDEX { ibmMvsRPingPacketSize, ibmMvsRPingTimeOut,                      
                ibmMvsRPingHostAddress }                                        
        ::= { ibmRemotePingTable 1 }                                            
                                                                                
        IbmRemotePingEntry ::=                                                  
          SEQUENCE                                                              
          {                                                                     
          ibmMvsRPingPacketSize    Integer32,                                   
          ibmMvsRPingTimeOut       Integer32,                                   
          ibmMvsRPingHostAddress   IpAddress,                                   
          ibmMvsRPingResponseTime  Integer32                                    
          }                                                                     
                                                                                
        ibmMvsRPingPacketSize OBJECT-TYPE                                       
        SYNTAX Integer32                                                        
        MAX-ACCESS not-accessible                                               
        STATUS current                                                          
        DESCRIPTION                                                             
           "Specifies the packet size in octets of the PING request.            
            Valid values for packet size are 0 or from 16 to 4096."             
        ::= { ibmRemotePingEntry 1 }                                            
                                                                                
        ibmMvsRPingTimeOut OBJECT-TYPE                                          
        SYNTAX Integer32                                                        
        MAX-ACCESS not-accessible                                               
        STATUS current                                                          
        DESCRIPTION                                                             
           "Specifies the time-out value, in seconds, for the actual            
            PING request made by the remote host. Value values for              
            time out are 0 or 3 to 15 seconds."                                 
        ::= { ibmRemotePingEntry 2 }                                            
                                                                                
        ibmMvsRPingHostAddress OBJECT-TYPE                                      
        SYNTAX IpAddress                                                        
        MAX-ACCESS not-accessible                                               
        STATUS current                                                          
        DESCRIPTION                                                             
           "Specifies the host address used on by PING request by               
            the remote host. The host address specified is                      
            required to be an ipAddress."                                       
        ::= { ibmRemotePingEntry 3 }                                            
                                                                                
        ibmMvsRPingResponseTime OBJECT-TYPE                                     
        SYNTAX Integer32                                                        
        MAX-ACCESS read-only                                                    
        STATUS current                                                          
        DESCRIPTION                                                             
           "The result of the PING request made by the remote host:             
            >0   Round-trip response time in milliseconds.                      
            -1   Internal error.                                                
            -2   ICMP echo request timed out.                                   
            -4   Incorrect packet size.                                         
            -5   Incorrect Time-out.                                            
            -6   Unknown destination address.                                   
            -7   Incorrect MIB instance format. The generic                     
                 noSuchInstance SNMP error could also occur if the              
                 instance specified is incorrect."                              
        ::= { ibmRemotePingEntry 4 }                                            
                                                                                
 ---------------------------------------------------------------------          
 -- ibmTcpipMvsSystem                                                           
 ---------------------------------------------------------------------          
                                                                                
     --                                                                         
     --         IBM TCPIP MVS System Group                                      
     --                                                                         
     --  Provides specific information and control for the                      
     --  IBM TCP/IP MVS Product. All simple objects are                         
     --  grouped within this object.                                            
     --                                                                         
                                                                                
     ibmMvsSubagentCacheTime OBJECT-TYPE                                        
     SYNTAX Integer32 (0 .. 3600)                                               
     MAX-ACCESS read-write                                                      
     STATUS current                                                             
     DESCRIPTION                                                                
           "Specifies the amount of time to wait for re-retrieval               
            of specific MIB data from target. A value of 0                      
            implies that every GET or GET-NEXT request should                   
            result in the re-retrieval of the needed data. Maximum              
            amount of time to cache is 1 hour (3600 seconds)."                  
     DEFVAL { 30 }                                                              
     ::= { ibmTcpipMvsSystem 1 }                                                
                                                                                
     ibmMvsIgnoreRedirect OBJECT-TYPE                                           
     SYNTAX INTEGER { process(0), ignore(1) }                                   
     MAX-ACCESS read-write                                                      
     STATUS current                                                             
     DESCRIPTION                                                                
           "IP Layer attribute, default of process redirects.                   
            current stack: IGNOREREDIRECT parm on                               
            ASSORTEDPARMS statement"                                            
     DEFVAL { process }                                                         
     ::= { ibmTcpipMvsSystem 2 }                                                
                                                                                
     ibmMvsArpCacheTimeout OBJECT-TYPE                                          
     SYNTAX Integer32 (60 .. 86400)                                             
     MAX-ACCESS read-write                                                      
     STATUS current                                                             
     DESCRIPTION                                                                
           "IF Layer attribute. ARP cache timeout - ARPAGE statement;           
            default= 1200 seconds; 60 <= ARPAGE <= 86400 (24 hours).            
            current stack: ARPAGE statement; default=                           
            20 minutes (1200 seconds). The value of this object is              
            expressed in seconds."                                              
     DEFVAL { 1200 }                                                            
     ::= { ibmTcpipMvsSystem 3 }                                                
                                                                                
     ibmMvsTcpKeepAliveTimer OBJECT-TYPE                                        
     SYNTAX Integer32 (0..35791)                                                
     MAX-ACCESS read-write                                                      
     STATUS current                                                             
     DESCRIPTION                                                                
           "TCP Keepalive timer, expressed in minutes.                          
            A value of 0 deactivates the timer."                                
     DEFVAL { 120 }                                                             
     ::= { ibmTcpipMvsSystem 4 }                                                
                                                                                
     ibmMvsTcpReceiveBufferSize OBJECT-TYPE                                     
     SYNTAX Integer32 (256..262144)                                             
     MAX-ACCESS read-write                                                      
     STATUS current                                                             
     DESCRIPTION                                                                
           "TCP Receive buffer size, expressed in bytes."                       
     DEFVAL { 16384 }                                                           
     ::= { ibmTcpipMvsSystem 5 }                                                
                                                                                
     ibmMvsTcpSendBufferSize OBJECT-TYPE                                        
     SYNTAX Integer32 (256..262144)                                             
     MAX-ACCESS read-write                                                      
     STATUS current                                                             
     DESCRIPTION                                                                
           "TCP Send buffer size, expressed in bytes."                          
     DEFVAL { 16384 }                                                           
     ::= { ibmTcpipMvsSystem 6 }                                                
                                                                                
     ibmMvsUdpChecksum OBJECT-TYPE                                              
     SYNTAX INTEGER { off(0), on(1) }                                           
     MAX-ACCESS read-write                                                      
     STATUS current                                                             
     DESCRIPTION                                                                
           "UDP checksum - on or off"                                           
     DEFVAL  {  on }                                                            
     ::= { ibmTcpipMvsSystem 7 }                                                
                                                                                
     ibmMvsIplDateAndTime OBJECT-TYPE                                           
     SYNTAX DateAndTime                                                         
     MAX-ACCESS read-only                                                       
     STATUS current                                                             
     DESCRIPTION                                                                
           "The date and time that this TCP/IP instance was                     
            started. sysUpTime provides the time from when                      
            the SNMP Agent was started, not corresponding TCP/IP                
            instance."                                                          
     ::= { ibmTcpipMvsSystem 8 }                                                
                                                                                
     ibmMvsNoUdpQueueLimit OBJECT-TYPE                                          
     SYNTAX INTEGER { queueLimit(0), noQueueLimit(1) }                          
     MAX-ACCESS read-write                                                      
     STATUS current                                                             
     DESCRIPTION                                                                
           "Indicates if the UDP queue limit of 163,840 bytes                   
            of UDP data per socket is in effect or not.                         
            163,840 is equal to 8K times 20 datagrams. This limit               
            is based on the total number of bytes, not datagrams."              
     DEFVAL { queueLimit }                                                      
     ::= { ibmTcpipMvsSystem 9 }                                                
                                                                                
     ibmMvsSoMaxConn OBJECT-TYPE                                                
     SYNTAX Integer32 (1..2147483647)                                           
     MAX-ACCESS read-write                                                      
     STATUS current                                                             
     DESCRIPTION                                                                
           "Maximum number of socket connections."                              
     DEFVAL { 10 }                                                              
     ::= { ibmTcpipMvsSystem 10 }                                               
                                                                                
     ibmMvsTcpipProcname OBJECT-TYPE                                            
     SYNTAX DisplayString (SIZE(1..8))                                          
     MAX-ACCESS read-only                                                       
     STATUS current                                                             
     DESCRIPTION                                                                
           "MVS Procname of this TCP/IP instance."                              
     ::= { ibmTcpipMvsSystem 11 }                                               
                                                                                
     ibmMvsTcpipAsid OBJECT-TYPE                                                
     SYNTAX Integer32                                                           
     MAX-ACCESS read-only                                                       
     STATUS current                                                             
     DESCRIPTION                                                                
           "MVS Address Space  ID of this TCP/IP instance."                     
     ::= { ibmTcpipMvsSystem 12 }                                               
                                                                                
     ibmMvsSourceVipaEnabled  OBJECT-TYPE                                       
     SYNTAX INTEGER { false(0), true(1) }                                       
     MAX-ACCESS read-only                                                       
     STATUS current                                                             
     DESCRIPTION                                                                
           "Indicates if set to true(1) that SOURCEVIPA support                 
            is enabled. This object can be changed via                          
            the ASSORTEDPARMS TCP/IP PROFILE statement."                        
     DEFVAL { false }                                                           
     ::= { ibmTcpipMvsSystem 13 }                                               
                                                                                
     ibmMvsOsasfSysplexName OBJECT-TYPE                                         
     SYNTAX DisplayString (SIZE(0..8))                                          
     MAX-ACCESS read-only                                                       
     STATUS current                                                             
     DESCRIPTION                                                                
           "Sysplex name, if unknown the value of the zero length               
            string"                                                             
     ::= { ibmTcpipMvsSystem 14 }                                               
                                                                                
     ibmMvsOsasfHostName OBJECT-TYPE                                            
     SYNTAX DisplayString (SIZE(0..8))                                          
     MAX-ACCESS read-only                                                       
     STATUS current                                                             
     DESCRIPTION                                                                
           "OSASF Host Name, if unknown the value of the zero length            
            string"                                                             
     ::= { ibmTcpipMvsSystem 15 }                                               
                                                                                
     ibmMvsOsasfProductVersion OBJECT-TYPE                                      
     SYNTAX DisplayString (SIZE(0..8))                                          
     MAX-ACCESS read-only                                                       
     STATUS current                                                             
     DESCRIPTION                                                                
           "version/release of product, if unknown the value of the             
            zero length string"                                                 
     ::= { ibmTcpipMvsSystem 16 }                                               
                                                                                
     ibmMvsPrimaryInterfaceIfIndex OBJECT-TYPE                                  
     SYNTAX Integer32                                                           
     MAX-ACCESS read-write                                                      
     STATUS current                                                             
     DESCRIPTION                                                                
           "The ifIndex of the designated primary interface.                    
            A value of zero implies that this option wasn't                     
            configured."                                                        
     DEFVAL { 0 }                                                               
     ::= { ibmTcpipMvsSystem 17 }                                               
                                                                                
     ibmMvsIpMaxReassemblySize  OBJECT-TYPE                                     
     SYNTAX Integer32                                                           
     MAX-ACCESS read-only                                                       
     STATUS current                                                             
     DESCRIPTION                                                                
           "The maximum ip reassembly size in units of                          
            octets."                                                            
     DEFVAL { 65535 }                                                           
     ::= { ibmTcpipMvsSystem 18 }                                               
                                                                                
     ibmMvsTcpRestrictLowPorts  OBJECT-TYPE                                     
     SYNTAX INTEGER { false(0), true(1) }                                       
     MAX-ACCESS read-write                                                      
     STATUS current                                                             
     DESCRIPTION                                                                
           "Indicates if TCP low ports are restricted to                        
            authorized servers/socket applications."                            
     DEFVAL { false }                                                           
     ::= { ibmTcpipMvsSystem 19 }                                               
                                                                                
     ibmMvsUdpRestrictLowPorts  OBJECT-TYPE                                     
     SYNTAX INTEGER { false(0), true(1) }                                       
     MAX-ACCESS read-write                                                      
     STATUS current                                                             
     DESCRIPTION                                                                
           "Indicates if UDP low ports are restricted to                        
            authorized servers/socket applications."                            
     DEFVAL { false }                                                           
     ::= { ibmTcpipMvsSystem 20 }                                               
                                                                                
     ibmMvsUdpSendBufferSize  OBJECT-TYPE                                       
     SYNTAX Integer32 (1..65535)                                                
     MAX-ACCESS read-write                                                      
     STATUS current                                                             
     DESCRIPTION                                                                
           "The default UDP send buffer size."                                  
     DEFVAL { 65535 }                                                           
     ::= { ibmTcpipMvsSystem 21 }                                               
                                                                                
     ibmMvsUdpRecvBufferSize  OBJECT-TYPE                                       
     SYNTAX Integer32 (1..65535)                                                
     MAX-ACCESS read-write                                                      
     STATUS current                                                             
     DESCRIPTION                                                                
           "The default UDP receive buffer size."                               
     DEFVAL { 65535 }                                                           
     ::= { ibmTcpipMvsSystem 22 }                                               
                                                                                
     ibmMvsTcpipStatisticsEnabled  OBJECT-TYPE                                  
     SYNTAX INTEGER { false(0), true(1) }                                       
     MAX-ACCESS read-only                                                       
     STATUS current                                                             
     DESCRIPTION                                                                
           "Indicates if set to true(1) that the generation                     
            of tcp/ip statistics is enabled. Statistics if                      
            enabled will be recorded at the SMF interval                        
            via SMF record subtype 5."                                          
     DEFVAL { false }                                                           
     ::= { ibmTcpipMvsSystem 23 }                                               
                                                                                
     ibmMvsFirewallEnabled  OBJECT-TYPE                                         
     SYNTAX INTEGER { false(0), true(1) }                                       
     MAX-ACCESS read-only                                                       
     STATUS current                                                             
     DESCRIPTION                                                                
           "Indicates if set to true(1) that firewall support                   
            is enabled. This object can be changed via                          
            the IPCONFIG TCP/IP PROFILE statement."                             
     DEFVAL { false }                                                           
     ::= { ibmTcpipMvsSystem 24 }                                               
                                                                                
     ibmMvsMaximumRetransmitTime OBJECT-TYPE                                    
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of 100th of a second."                                        
     DEFVAL { 120000 }                                                          
     ::= { ibmTcpipMvsSystem 25 }                                               
                                                                                
     ibmMvsMinimumRetransmitTime OBJECT-TYPE                                    
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of 100th of a second."                                        
     DEFVAL { 500 }                                                             
     ::= { ibmTcpipMvsSystem 26 }                                               
                                                                                
     ibmMvsRoundTripGain OBJECT-TYPE                                            
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of .0001."                                                    
     DEFVAL { 125 }                                                             
     ::= { ibmTcpipMvsSystem 27 }                                               
                                                                                
     ibmMvsVarianceGain OBJECT-TYPE                                             
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of .0001."                                                    
     DEFVAL { 250 }                                                             
     ::= { ibmTcpipMvsSystem 28 }                                               
                                                                                
     ibmMvsVarianceMultiplier OBJECT-TYPE                                       
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of .0001."                                                    
     DEFVAL { 2000 }                                                            
     ::= { ibmTcpipMvsSystem 29 }                                               
                                                                                
     ibmMvsSendGarbageEnabled OBJECT-TYPE                                       
     SYNTAX INTEGER { false(0), true(1) }                                       
     MAX-ACCESS read-only                                                       
     STATUS current                                                             
     DESCRIPTION                                                                
           "If true(1) indicates that the TCP option SENDGARBAGE                
            is enabled."                                                        
     DEFVAL { false }                                                           
     ::= { ibmTcpipMvsSystem 30 }                                               
                                                                                
 ---------------------------------------------------------------------          
 -- ibmTcpipMvsInterfaceGroup                                                   
 ---------------------------------------------------------------------          
                                                                                
     --                                                                         
     --         IBM TCPIP MVS Device Table                                      
     --                                                                         
     ibmTcpipMvsDeviceTable OBJECT-TYPE                                         
     SYNTAX SEQUENCE OF IbmTcpipMvsDeviceEntry                                  
     MAX-ACCESS not-accessible                                                  
     STATUS current                                                             
     DESCRIPTION                                                                
          "Defines the device definition known to an IBM MVS                    
           TCP/IP system. A virtual interface entry exists for                  
           every entry in this table."                                          
     ::= { ibmTcpipMvsInterfaceGroup 1 }                                        
                                                                                
     ibmTcpipMvsDeviceEntry OBJECT-TYPE                                         
     SYNTAX IbmTcpipMvsDeviceEntry                                              
     MAX-ACCESS not-accessible                                                  
     STATUS current                                                             
     DESCRIPTION                                                                
          "Descibes a particular device definition"                             
     INDEX { ifIndex }                                                          
     ::= { ibmTcpipMvsDeviceTable 1 }                                           
                                                                                
     IbmTcpipMvsDeviceEntry ::=                                                 
          SEQUENCE                                                              
          {                                                                     
          ibmMvsDeviceType                 DeviceLinkTypes,                     
          ibmMvsDeviceBaseNumber           OCTET STRING,                        
          ibmMvsDeviceIoBufferSize         Integer32,                           
          ibmMvsDeviceAutoRestart          INTEGER,                             
          ibmMvsDeviceNetmanEnabled        INTEGER,                             
          ibmMvsDeviceHostClawName         DisplayString,                       
          ibmMvsDeviceWorkstationClawName  DisplayString,                       
          ibmMvsDeviceReadBuffers          Integer32,                           
          ibmMvsDeviceReadSize             Integer32,                           
          ibmMvsDeviceWriteBuffers         Integer32,                           
          ibmMvsDeviceWriteSize            Integer32,                           
          ibmMvsDeviceProcname             DisplayString,                       
          ibmMvsDeviceIncomingSvcEnabled   INTEGER,                             
          ibmMvsDeviceLuName               DisplayString                        
          }                                                                     
                                                                                
     ibmMvsDeviceType OBJECT-TYPE                                               
     SYNTAX DeviceLinkTypes                                                     
     MAX-ACCESS read-only                                                       
     STATUS current                                                             
     DESCRIPTION                                                                
           "Indicates the device type."                                         
     ::= { ibmTcpipMvsDeviceEntry 1 }                                           
                                                                                
     ibmMvsDeviceBaseNumber OBJECT-TYPE                                         
     SYNTAX OCTET STRING (SIZE(2))                                              
     MAX-ACCESS read-only                                                       
     STATUS current                                                             
     DESCRIPTION                                                                
          "If this entry is for a CTC, HCH or Vipa device then this             
           object represents its base device number. For a LCS                  
           device this object represents the lcs address. For a                 
           device this object represents the device number. For a               
           A value of                                                           
           of 0 implies that this object is not valid for the                   
           associating device table entry."                                     
     ::= { ibmTcpipMvsDeviceEntry 2 }                                           
                                                                                
     ibmMvsDeviceIoBufferSize OBJECT-TYPE                                       
     SYNTAX Integer32 (32768 .. 65535)                                          
     MAX-ACCESS read-only                                                       
     STATUS current                                                             
     DESCRIPTION                                                                
         "The I/O buffersize attribute for this device definition.              
           This is only value for a CTC Device. A reported value                
           of -1 implies that the corresponding device doesn't                  
            not support this attribute."                                        
     DEFVAL { 32768 }                                                           
     ::= { ibmTcpipMvsDeviceEntry 3 }                                           
                                                                                
     ibmMvsDeviceAutoRestart  OBJECT-TYPE                                       
     SYNTAX INTEGER { false(0), true(1) }                                       
     MAX-ACCESS read-only                                                       
     STATUS current                                                             
     DESCRIPTION                                                                
        "A value of true indicates that this device was defined                 
         as autorestartable. False indicates that it was not."                  
     ::= { ibmTcpipMvsDeviceEntry 4 }                                           
                                                                                
     ibmMvsDeviceNetmanEnabled OBJECT-TYPE                                      
     SYNTAX INTEGER { invalid(-1), false(0), true(1) }                          
     MAX-ACCESS read-only                                                       
     STATUS current                                                             
     DESCRIPTION                                                                
        "A value of true indicates that this is a LCS device that               
         was defined to support the 3172 ICP MIB. A reported                    
         value of invalid (-1) implies that this object is                      
         invalid for the corresponding device table entry."                     
     DEFVAL { false }                                                           
     ::= { ibmTcpipMvsDeviceEntry 5 }                                           
                                                                                
     ibmMvsDeviceHostClawName OBJECT-TYPE                                       
     SYNTAX DisplayString (SIZE(0..8))                                          
     MAX-ACCESS read-only                                                       
     STATUS current                                                             
     DESCRIPTION                                                                
        "A non NULL OCTET STRING implies that this is the Host Claw             
         Name for a CLAW Device definition."                                    
     ::= { ibmTcpipMvsDeviceEntry 6 }                                           
                                                                                
     ibmMvsDeviceWorkstationClawName  OBJECT-TYPE                               
     SYNTAX DisplayString (SIZE(0..8))                                          
     MAX-ACCESS read-only                                                       
     STATUS current                                                             
     DESCRIPTION                                                                
        "A non NULL OCTET STRING implies that this is the Workstation           
         Claw name for a CLAW Device definition."                               
     ::= { ibmTcpipMvsDeviceEntry 7 }                                           
                                                                                
     ibmMvsDeviceReadBuffers OBJECT-TYPE                                        
     SYNTAX Integer32                                                           
     MAX-ACCESS read-only                                                       
     STATUS current                                                             
     DESCRIPTION                                                                
        "The number of read buffers for either a CLAW RS/6000 IP                
         or a CDLC device definition. A value of -1 implies that                
         the value of this object is invalid."                                  
     ::= { ibmTcpipMvsDeviceEntry 8 }                                           
                                                                                
     ibmMvsDeviceReadSize  OBJECT-TYPE                                          
     SYNTAX Integer32                                                           
     MAX-ACCESS read-only                                                       
     STATUS current                                                             
     DESCRIPTION                                                                
        "The read buffer size for either a CLAW RS/6000 IP                      
         or a CDLC device definition. A value of -1 implies that                
         the value of this object is invalid."                                  
     ::= { ibmTcpipMvsDeviceEntry 9 }                                           
                                                                                
     ibmMvsDeviceWriteBuffers OBJECT-TYPE                                       
     SYNTAX Integer32                                                           
     MAX-ACCESS read-only                                                       
     STATUS current                                                             
     DESCRIPTION                                                                
        "The number of write buffers for either a CLAW RS/6000 IP               
         or a CDLC device definition. A value of -1 implies that                
         the value of this object is invalid."                                  
     ::= { ibmTcpipMvsDeviceEntry 10 }                                          
                                                                                
     ibmMvsDeviceWriteSize OBJECT-TYPE                                          
     SYNTAX Integer32                                                           
     MAX-ACCESS read-only                                                       
     STATUS current                                                             
     DESCRIPTION                                                                
        "The write buffer size for either a CLAW RS/6000 IP                     
         or a CDLC device definition. A value of -1 implies that                
         the value of this object is invalid."                                  
     ::= { ibmTcpipMvsDeviceEntry 11 }                                          
                                                                                
     ibmMvsDeviceProcname OBJECT-TYPE                                           
     SYNTAX DisplayString (SIZE(0..8))                                          
     MAX-ACCESS read-only                                                       
     STATUS current                                                             
     DESCRIPTION                                                                
        "A non NULL OCTET STRING implies that this is the procname              
         for an X25NPSI, SNA LU0, or SNA LU6.2 Device definition."              
     ::= { ibmTcpipMvsDeviceEntry 12 }                                          
                                                                                
     ibmMvsDeviceIncomingSvcEnabled OBJECT-TYPE                                 
     SYNTAX INTEGER { false(0), true(1) }                                       
     MAX-ACCESS read-only                                                       
     STATUS current                                                             
     DESCRIPTION                                                                
        "This object is valid only for an ATM Device. If true then              
         incoming SVCs will be allowed. A value of false for an                 
         ATM Device implies that incoming SVC call setup will be                
         rejected."                                                             
     DEFVAL { true }                                                            
     ::= { ibmTcpipMvsDeviceEntry 13 }                                          
                                                                                
     ibmMvsDeviceLuName   OBJECT-TYPE                                           
     SYNTAX DisplayString (SIZE(0..8))                                          
     MAX-ACCESS read-only                                                       
     STATUS current                                                             
     DESCRIPTION                                                                
        "A non NULL OCTET STRING implies that this is the Logical               
         Unit name for a SNA LU0 Device definition."                            
     ::= { ibmTcpipMvsDeviceEntry 14 }                                          
                                                                                
                                                                                
                                                                                
     --                                                                         
     --         IBM TCPIP MVS Link Table                                        
     --                                                                         
                                                                                
     ibmTcpipMvsLinkTable OBJECT-TYPE                                           
     SYNTAX SEQUENCE OF IbmTcpipMvsLinkEntry                                    
     MAX-ACCESS not-accessible                                                  
     STATUS current                                                             
     DESCRIPTION                                                                
          "Defines the link definition known to an IBM MVS                      
           TCP/IP system. A physical interface entry exists                     
           for every entry in this table."                                      
     ::= { ibmTcpipMvsInterfaceGroup 2 }                                        
                                                                                
     ibmTcpipMvsLinkEntry OBJECT-TYPE                                           
     SYNTAX IbmTcpipMvsLinkEntry                                                
     MAX-ACCESS not-accessible                                                  
     STATUS current                                                             
     DESCRIPTION                                                                
          "Descibes a particular link definition"                               
     INDEX { ifIndex }                                                          
     ::= { ibmTcpipMvsLinkTable 1 }                                             
                                                                                
     IbmTcpipMvsLinkEntry ::=                                                   
          SEQUENCE                                                              
          {                                                                     
          ibmMvsLinkType            DeviceLinkTypes,                            
          ibmMvsLinkDeviceIndex    Integer32,                                   
          ibmMvsLinkAdapterAddr    Integer32,                                   
          ibmMvsLinkNumber         Integer32,                                   
          ibmMvsLinkIbmtrCanonical INTEGER,                                     
          ibmMvsLinkIbmtrBcast     INTEGER                                      
          }                                                                     
                                                                                
     ibmMvsLinkType OBJECT-TYPE                                                 
     SYNTAX DeviceLinkTypes                                                     
     MAX-ACCESS read-only                                                       
     STATUS current                                                             
     DESCRIPTION                                                                
           "Indicates the link type."                                           
     ::= { ibmTcpipMvsLinkEntry 1 }                                             
                                                                                
     ibmMvsLinkDeviceIndex OBJECT-TYPE                                          
     SYNTAX Integer32                                                           
     MAX-ACCESS read-only                                                       
     STATUS current                                                             
     DESCRIPTION                                                                
           "ifIndex of corresponding DEVICE entry."                             
     ::= { ibmTcpipMvsLinkEntry 2 }                                             
                                                                                
     ibmMvsLinkAdapterAddr OBJECT-TYPE                                          
     SYNTAX Integer32                                                           
     MAX-ACCESS read-only                                                       
     STATUS current                                                             
     DESCRIPTION                                                                
           "The adapter address associated with this link                       
            definition. A value of -1 indicates that this                       
            object is invalid for the corresponding link table                  
            entry."                                                             
     DEFVAL { -1 }                                                              
     ::= { ibmTcpipMvsLinkEntry 3 }                                             
                                                                                
     ibmMvsLinkNumber OBJECT-TYPE                                               
     SYNTAX Integer32                                                           
     MAX-ACCESS read-only                                                       
     STATUS current                                                             
     DESCRIPTION                                                                
           "The link number associated with this link                           
            definition. A value of -1 indicates that this                       
            object is invalid for the corresponding link table                  
            entry."                                                             
     DEFVAL { -1 }                                                              
     ::= { ibmTcpipMvsLinkEntry 4 }                                             
                                                                                
     ibmMvsLinkIbmtrCanonical OBJECT-TYPE                                       
     SYNTAX INTEGER { invalid(-1), false(0), true(1) }                          
     MAX-ACCESS read-only                                                       
     STATUS current                                                             
     DESCRIPTION                                                                
        "For a IBMTR LCS Link a value of true implies that this                 
         link was defined with a value of CANONICAL. A reported                 
         value of -1 implies that object is not supported by the                
         associating link."                                                     
     DEFVAL { invalid }                                                         
     ::= { ibmTcpipMvsLinkEntry 5 }                                             
                                                                                
     ibmMvsLinkIbmtrBcast  OBJECT-TYPE                                          
     SYNTAX INTEGER {                                                           
                            invalid(-1),                                        
                            nobcast(0),                                         
                            allringsbcast(1),                                   
                            localbcast(2)                                       
                          }                                                     
     MAX-ACCESS read-only                                                       
     STATUS current                                                             
     DESCRIPTION                                                                
        "For a IBMTR LCS Link provide the bcast setting otherwise               
         a value of -1 for invalid would be reported for this                   
         object."                                                               
     DEFVAL  { invalid }                                                        
     ::= { ibmTcpipMvsLinkEntry 6 }                                             
                                                                                
 ---------------------------------------------------------------------          
 -- ibmTcpipMvsPortGroup                                                        
 ---------------------------------------------------------------------          
                                                                                
     --                                                                         
     --       IBM TCPIP Port Table                                              
     --                                                                         
                                                                                
     ibmTcpipMvsPortTable OBJECT-TYPE                                           
     SYNTAX SEQUENCE OF IbmTcpipMvsPortEntry                                    
     MAX-ACCESS not-accessible                                                  
     STATUS current                                                             
     DESCRIPTION                                                                
          "Prereserves ports within a TCP/IP address space."                    
     ::= { ibmTcpipMvsPortGroup 1 }                                             
                                                                                
     ibmTcpipMvsPortEntry OBJECT-TYPE                                           
     SYNTAX IbmTcpipMvsPortEntry                                                
     MAX-ACCESS not-accessible                                                  
     STATUS current                                                             
     DESCRIPTION                                                                
          "Defines a single ibmTcpipMvsPortTable entry."                        
     INDEX { ibmMvsPortNumberLow, ibmMvsPortNumberHigh,                         
             ibmMvsPortProtocol, ibmMvsPortProcName }                           
     ::= { ibmTcpipMvsPortTable 1 }                                             
                                                                                
     IbmTcpipMvsPortEntry ::=                                                   
          SEQUENCE                                                              
          {                                                                     
          ibmMvsPortNumberLow    Integer32,                                     
          ibmMvsPortNumberHigh   Integer32,                                     
          ibmMvsPortProtocol       INTEGER,                                     
          ibmMvsPortProcName     DisplayString,                                 
          ibmMvsPortAutoLoggable  INTEGER,                                      
          ibmMvsPortDelayAcks    INTEGER,                                       
          ibmMvsPortOptMaxSegmentSize INTEGER,                                  
          ibmMvsPortSharePort    INTEGER                                        
          }                                                                     
                                                                                
     ibmMvsPortNumberLow OBJECT-TYPE                                            
     SYNTAX Integer32                                                           
     MAX-ACCESS read-only                                                       
     STATUS current                                                             
     DESCRIPTION                                                                
           "Low port number of entry."                                          
      ::= { ibmTcpipMvsPortEntry 1 }                                            
                                                                                
     ibmMvsPortNumberHigh OBJECT-TYPE                                           
     SYNTAX Integer32                                                           
     MAX-ACCESS read-only                                                       
     STATUS current                                                             
     DESCRIPTION                                                                
           "High port number of entry."                                         
      ::= { ibmTcpipMvsPortEntry 2 }                                            
                                                                                
     ibmMvsPortProtocol OBJECT-TYPE                                             
     SYNTAX INTEGER { tcp(0), udp(1) }                                          
     MAX-ACCESS read-only                                                       
     STATUS current                                                             
     DESCRIPTION                                                                
           "The protocol of the associating port entry."                        
      ::= { ibmTcpipMvsPortEntry 3 }                                            
                                                                                
     ibmMvsPortProcName OBJECT-TYPE                                             
     SYNTAX DisplayString (SIZE(1..8))                                          
     MAX-ACCESS read-only                                                       
     STATUS current                                                             
     DESCRIPTION                                                                
           "Text Name of the associating mvs procedure."                        
      ::= { ibmTcpipMvsPortEntry 4 }                                            
                                                                                
     ibmMvsPortAutoLoggable OBJECT-TYPE                                         
     SYNTAX INTEGER { false(0), true(1) }                                       
     MAX-ACCESS read-only                                                       
     STATUS current                                                             
     DESCRIPTION                                                                
           "Should proc be autologged."                                         
     DEFVAL { true }                                                            
     ::= { ibmTcpipMvsPortEntry 5 }                                             
                                                                                
     ibmMvsPortDelayAcks OBJECT-TYPE                                            
     SYNTAX INTEGER { false(0), true(1) }                                       
     MAX-ACCESS read-only                                                       
     STATUS current                                                             
     DESCRIPTION                                                                
           "A value of true implies that DELAYACKS was selected                 
            for this port entry."                                               
     DEFVAL { false }                                                           
     ::= { ibmTcpipMvsPortEntry 6 }                                             
                                                                                
     ibmMvsPortOptMaxSegmentSize OBJECT-TYPE                                    
     SYNTAX INTEGER { false(0), true(1) }                                       
     MAX-ACCESS read-only                                                       
     STATUS current                                                             
     DESCRIPTION                                                                
           "A value of true implies that the Optimal Maximum                    
            Segment Size option was selected for this port entry."              
     DEFVAL { false }                                                           
     ::= { ibmTcpipMvsPortEntry 7 }                                             
                                                                                
     ibmMvsPortSharePort OBJECT-TYPE                                            
     SYNTAX INTEGER { false(0), true(1) }                                       
     MAX-ACCESS read-only                                                       
     STATUS current                                                             
     DESCRIPTION                                                                
           "A value of true implies that SHAREPORT was selected                 
            for this port entry."                                               
     DEFVAL { false }                                                           
     ::= { ibmTcpipMvsPortEntry 8 }                                             
                                                                                
 ---------------------------------------------------------------------          
 -- ibmTcpipMvsRouteGroup                                                       
 ---------------------------------------------------------------------          
                                                                                
      --                                                                        
      --   IBM TCPIP Gateway Table                                              
      --                                                                        
                                                                                
     ibmTcpipMvsGatewayTable OBJECT-TYPE                                        
     SYNTAX SEQUENCE OF IbmTcpipMvsGatewayEntry                                 
     MAX-ACCESS not-accessible                                                  
     STATUS current                                                             
     DESCRIPTION                                                                
          "Extends ipForwardTable to support gateway semantic."                 
     ::= { ibmTcpipMvsRouteGroup 1 }                                            
                                                                                
     ibmTcpipMvsGatewayEntry OBJECT-TYPE                                        
     SYNTAX IbmTcpipMvsGatewayEntry                                             
     MAX-ACCESS not-accessible                                                  
     STATUS current                                                             
     DESCRIPTION                                                                
          "Descibes a particular gateway entry"                                 
     AUGMENTS { ipForwardEntry }                                                
     ::= { ibmTcpipMvsGatewayTable 1 }                                          
                                                                                
     IbmTcpipMvsGatewayEntry ::=                                                
          SEQUENCE                                                              
          {                                                                     
          ibmMvsGatewayMaximumRetransmitTime       Integer32,                   
          ibmMvsGatewayMinimumRetransmitTime       Integer32,                   
          ibmMvsGatewayRoundTripGain               Integer32,                   
          ibmMvsGatewayVarianceGain                Integer32,                   
          ibmMvsGatewayVarianceMultiplier          Integer32,                   
          ibmMvsGatewayDelayAcks                   INTEGER                      
          }                                                                     
                                                                                
     ibmMvsGatewayMaximumRetransmitTime OBJECT-TYPE                             
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of 100th of a second."                                        
     DEFVAL { 6000 }                                                            
     ::= { ibmTcpipMvsGatewayEntry 1 }                                          
                                                                                
     ibmMvsGatewayMinimumRetransmitTime OBJECT-TYPE                             
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of 100th of a second."                                        
     DEFVAL { 75 }                                                              
     ::= { ibmTcpipMvsGatewayEntry 2 }                                          
                                                                                
     ibmMvsGatewayRoundTripGain OBJECT-TYPE                                     
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of .0001."                                                    
     DEFVAL { 1200 }                                                            
     ::= { ibmTcpipMvsGatewayEntry 3 }                                          
                                                                                
     ibmMvsGatewayVarianceGain OBJECT-TYPE                                      
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of .0001."                                                    
     DEFVAL { 2500 }                                                            
     ::= { ibmTcpipMvsGatewayEntry 4 }                                          
                                                                                
     ibmMvsGatewayVarianceMultiplier OBJECT-TYPE                                
     SYNTAX Integer32                                                           
     MAX-ACCESS read-only                                                       
     STATUS current                                                             
     DESCRIPTION                                                                
           "Used in the TCP/IP re-transmission time-out calculation             
            to determine how long to wait for an acknowledgement                
            before resending a packet. Expressed as a integer in                
            units of .0001."                                                    
     DEFVAL { 20000 }                                                           
     ::= { ibmTcpipMvsGatewayEntry 5 }                                          
                                                                                
     ibmMvsGatewayDelayAcks OBJECT-TYPE                                         
     SYNTAX INTEGER { false(0), true(1) }                                       
     MAX-ACCESS read-only                                                       
     STATUS current                                                             
     DESCRIPTION                                                                
           "Delays transmission of acknowledgements when a packet               
            is received with the PUSH bit on in the TCP header. The             
            DELAYACKS parameter on the GATEWAY statement only                   
            applies to the TCP protocol and only affects                        
            acknowledgements returned to the foreign host. To                   
            delay acknowledgements on a TCP/IP port connection                  
            use the DELAYACKS parameter on the PORT statement."                 
     DEFVAL { false }                                                           
     ::= { ibmTcpipMvsGatewayEntry 6 }                                          
                                                                                
 ---------------------------------------------------------------------          
 -- ibmTcpipMvsAtmGroup                                                         
 ---------------------------------------------------------------------          
                                                                                
     osasfChannelTable OBJECT-TYPE                                              
     SYNTAX SEQUENCE OF OsasfChannelEntry                                       
     MAX-ACCESS not-accessible                                                  
     STATUS current                                                             
     DESCRIPTION                                                                
        "Indexed by ifIndex. One entry in this table will exist per             
         ATM Device Interface.  If the values for objects                       
         ibmMvsAtmOsasfCurLparName/Num are not the same as the values           
         for objects ibmMvsAtmOsasfManParnName/Num then the OSA/SF              
         running in the current LPAR is not the managing OSA/SF for             
         this Device.  SNMP Set commands for ifAdminStatus (to enable           
         or disable an ATM port using the ATM aal5 interface ifIndex)           
         or for ibmMvsAtmPortIpAddress (to set an IP address at the             
         ATM port) will be rejected by OSA/SF if the OSA/SF in the              
         current LPAR is not the managing OSA/SF for this Device."              
     ::= { ibmTcpipMvsAtmGroup 1 }                                              
                                                                                
     osasfChannelEntry OBJECT-TYPE                                              
     SYNTAX OsasfChannelEntry                                                   
     MAX-ACCESS not-accessible                                                  
     STATUS current                                                             
     DESCRIPTION                                                                
        "Definition of a single entry in the osasfChannelTable.                 
         Indexed by the ifIndex of the corresponding DEVICE interface."         
     INDEX { ifIndex }                                                          
     ::= { osasfChannelTable 1 }                                                
                                                                                
     OsasfChannelEntry ::=                                                      
     SEQUENCE                                                                   
       {                                                                        
       ibmMvsAtmOsasfChannelNumber              Integer32,                      
       ibmMvsAtmOsasfChannelType                 INTEGER,                       
       ibmMvsAtmOsasfChannelSubType             INTEGER,                        
       ibmMvsAtmOsasfChannelMode                 INTEGER,                       
       ibmMvsAtmOsasfChannelHwModel             INTEGER,                        
       ibmMvsAtmOsasfChannelState                 INTEGER,                      
       ibmMvsAtmOsasfChannelShared               INTEGER,                       
       ibmMvsAtmOsasfChannelNumPorts            Integer32,                      
       ibmMvsAtmOsasfChannelDeterNodeDesc       OCTET STRING,                   
       ibmMvsAtmOsasfChannelControlUnitNumber   Integer32,                      
       ibmMvsAtmOsasfChannelCodeLevel           Integer32,                      
       ibmMvsAtmOsasfChannelEcLevel             DisplayString,                  
       ibmMvsAtmOsasfChannelCurLparName         DisplayString,                  
       ibmMvsAtmOsasfChannelCurLparNum          Integer32,                      
       ibmMvsAtmOsasfChannelManParnName         DisplayString,                  
       ibmMvsAtmOsasfChannelManParnNum          Integer32,                      
       ibmMvsAtmOsasfChannelDate                DisplayString,                  
       ibmMvsAtmOsasfChannelTime                DisplayString,                  
       ibmMvsAtmOsasfChannelFlashLevel          DisplayString,                  
       ibmMvsAtmOsasfChannelVtamId                Integer32                     
       }                                                                        
                                                                                
     ibmMvsAtmOsasfChannelNumber OBJECT-TYPE                                    
     SYNTAX Integer32                                                           
     MAX-ACCESS read-only                                                       
     STATUS current                                                             
     DESCRIPTION                                                                
           "The channel number for this interface"                              
     ::= { osasfChannelEntry 1 }                                                
                                                                                
     ibmMvsAtmOsasfChannelType OBJECT-TYPE                                      
     SYNTAX INTEGER { other(1), osa(18) }                                       
     MAX-ACCESS read-only                                                       
     STATUS current                                                             
     DESCRIPTION                                                                
           "The channel type, should always be osa"                             
     ::= { osasfChannelEntry 2 }                                                
                                                                                
     ibmMvsAtmOsasfChannelSubType OBJECT-TYPE                                   
     SYNTAX INTEGER {                                                           
                      invalid(-1),                                              
                      unknown(0),                                               
                      ethernet(1),                                              
                      tokenRing(2),                                             
                      twoTokenRingPorts(3),                                     
                      tokenRingAndEthernetPorts(4),                             
                      ethernetAndTokenRingPorts(5),                             
                      twoEthernetPorts(6),                                      
                      fddi(7),                                                  
                      noPortsDefined(8),                                        
                      atmNativeOrIpForwarding(9),                               
                      oneLogicalEthernetPort(10),                               
                      oneLogicalTokenRingPort(11)                               
                    }                                                           
     MAX-ACCESS read-only                                                       
     STATUS current                                                             
     DESCRIPTION                                                                
           "Indicates how the channel is configured.                            
            A valid of -1 should not occur for this                             
            object."                                                            
     ::= { osasfChannelEntry 3 }                                                
                                                                                
     ibmMvsAtmOsasfChannelMode OBJECT-TYPE                                      
     SYNTAX INTEGER {                                                           
                           other(1),                                            
                           passthruMode(2),                                     
                           snaMode(3),                                          
                           atmLeTcpipMode(4),                                   
                           atmLeSnaMode(5),                                     
                           atmLeSnaTcpipMode(6),                                
                           atmNativeMode(7),                                    
                           atmIpFwdMode(8)                                      
                         }                                                      
     MAX-ACCESS read-only                                                       
     STATUS current                                                             
     DESCRIPTION                                                                
           "Config mode of the OSA2 card."                                      
     ::= { osasfChannelEntry 4 }                                                
                                                                                
     ibmMvsAtmOsasfChannelHwModel OBJECT-TYPE                                   
     SYNTAX INTEGER {                                                           
                           undefined(0),                                        
                           osa1(1),                                             
                           osa2(2),                                             
                           osa2Atm(3)                                           
                         }                                                      
     MAX-ACCESS read-only                                                       
     STATUS current                                                             
     DESCRIPTION                                                                
           "Hardware model of the channel. The field NDModelNum                 
            contained in ibmMvsAtmOsasfChannelDeterNodeDesc                     
            is a char(3) field that contains in readable format of              
            this object's value."                                               
     ::= { osasfChannelEntry 5 }                                                
                                                                                
     ibmMvsAtmOsasfChannelState   OBJECT-TYPE                                   
     SYNTAX INTEGER {                                                           
                           online(1),                                           
                           notinst(3),                                          
                           offline(5)                                           
                         }                                                      
     MAX-ACCESS read-only                                                       
     STATUS current                                                             
     DESCRIPTION                                                                
           "Hardware channel state: online, offline, or                         
            not installed."                                                     
     ::= { osasfChannelEntry 6 }                                                
                                                                                
     ibmMvsAtmOsasfChannelShared  OBJECT-TYPE                                   
     SYNTAX INTEGER { no(0), yes(1) }                                           
     MAX-ACCESS read-only                                                       
     STATUS current                                                             
     DESCRIPTION                                                                
           "An OSA Channel can be shared across multiple                        
            LPARs. This object indicates if this channel                        
            is currently being shared."                                         
     ::= { osasfChannelEntry 7 }                                                
                                                                                
     ibmMvsAtmOsasfChannelNumPorts  OBJECT-TYPE                                 
     SYNTAX Integer32                                                           
     MAX-ACCESS read-only                                                       
     STATUS current                                                             
     DESCRIPTION                                                                
           "Number of physical ports on OSA channel."                           
     ::= { osasfChannelEntry 8 }                                                
                                                                                
     ibmMvsAtmOsasfChannelDeterNodeDesc OBJECT-TYPE                             
     SYNTAX  OCTET STRING (SIZE(32))                                            
     MAX-ACCESS read-only                                                       
     STATUS current                                                             
     DESCRIPTION                                                                
           "Describes the generic node descriptor layout.                       
            This object represents the ND obtained from the                     
            CHSC instruction:                                                   
                                       /* ND Flags                */            
            int   bValidity      :3;   /* 1:is ND valid           */            
            int   bNodeType      :1;   /* 1:0=dev,1=chnlsubstm nod*/            
            int   bInternal      :1;   /* internal(1)/external(0) */            
            int   bCHPinvalid    :1;   /* IF =1,NDCHPID is invalid*/            
            int   bNDRsvd1       :2;   /* spare bits for alignment*/            
            char  NDRsvd1;             /* reserved by architecture*/            
            char  NDClass;             /* Class for subsystem node*/            
            char  NDCHPID;             /* CHP ID for specified int*/            
         6];        /* type number of the SDC  */                               
            char  NDModelNum[3];       /* ND model number in the                
                                          form of 3 EBCDIC OCTETS */            
            char  NDMfgr[3];           /* ND manufacturer in the                
                                          form of 3 EBCDIC OCTETS */            
            char  NDMfgrPlant[2];      /* ND plant of manufacture               
                                          (2 EBCDIC OCTETS)       */            
            char  NDSeqNum[12];        /* ND sequence number                    
                                          (12 EBCDIC OCTETS)      */            
            char  NDTag[2];            /* ND tag                  */"           
     ::= { osasfChannelEntry 9 }                                                
                                                                                
     ibmMvsAtmOsasfChannelControlUnitNumber OBJECT-TYPE                         
     SYNTAX  Integer32                                                          
     MAX-ACCESS read-only                                                       
     STATUS current                                                             
     DESCRIPTION                                                                
           "The control unit number associated with the OSA Channel."           
     ::= { osasfChannelEntry 10 }                                               
                                                                                
     ibmMvsAtmOsasfChannelCodeLevel OBJECT-TYPE                                 
     SYNTAX  Integer32                                                          
     MAX-ACCESS read-only                                                       
     STATUS current                                                             
     DESCRIPTION                                                                
           "ibmMvsAtmOsasfChannelCodeLevel is the firmware                      
            (or micro code level) of the OSA card.  For example,                
            OSA2-ATM card level 05.60 would be represented as                   
            0x0560 by this object."                                             
     ::= { osasfChannelEntry 11 }                                               
                                                                                
     ibmMvsAtmOsasfChannelEcLevel OBJECT-TYPE                                   
     SYNTAX  DisplayString (SIZE(0..8))                                         
     MAX-ACCESS read-only                                                       
     STATUS current                                                             
     DESCRIPTION                                                                
           "The Box EC Level Identifier of the OSA Card which                   
            identifies the current Engineering Change (EC) Level of             
            this OSA Card (Channel)."                                           
     ::= { osasfChannelEntry 12 }                                               
                                                                                
     ibmMvsAtmOsasfChannelCurLparName OBJECT-TYPE                               
     SYNTAX  DisplayString (SIZE(0..8))                                         
     MAX-ACCESS read-only                                                       
     STATUS current                                                             
     DESCRIPTION                                                                
           "LPAR name of the OSA/SF from which this data was                    
            retrieved from"                                                     
     ::= { osasfChannelEntry 13 }                                               
                                                                                
     ibmMvsAtmOsasfChannelCurLparNum OBJECT-TYPE                                
     SYNTAX  Integer32                                                          
     MAX-ACCESS read-only                                                       
     STATUS current                                                             
     DESCRIPTION                                                                
           "LPAR number of the OSA/SF from which this data was                  
            retrieved from"                                                     
     ::= { osasfChannelEntry 14 }                                               
                                                                                
     ibmMvsAtmOsasfChannelManParnName OBJECT-TYPE                               
     SYNTAX  DisplayString (SIZE(0..8))                                         
     MAX-ACCESS read-only                                                       
     STATUS current                                                             
     DESCRIPTION                                                                
           "LPAR name of the OSA Support Facility managing this                 
            channel. Only one OSA/SF can manage a OSA Channel                   
            within an MVS Sysplex even though multiple OSA/SFs                  
            can retrieve information from the same OSA Channel."                
     ::= { osasfChannelEntry 15 }                                               
                                                                                
     ibmMvsAtmOsasfChannelManParnNum  OBJECT-TYPE                               
     SYNTAX  Integer32                                                          
     MAX-ACCESS read-only                                                       
     STATUS current                                                             
     DESCRIPTION                                                                
           "LPAR number of the OSA Support Facility managing this               
            channel (set to 0xFFFF if not being managed by a                    
            OSA/SF)."                                                           
     ::= { osasfChannelEntry 16 }                                               
                                                                                
     ibmMvsAtmOsasfChannelDate OBJECT-TYPE                                      
     SYNTAX  DisplayString (SIZE(1..12))                                        
     MAX-ACCESS read-only                                                       
     STATUS current                                                             
     DESCRIPTION                                                                
           "Date on this channel (set to 'NOTVALID' if there                    
            the disk serving function is not active)."                          
     ::= { osasfChannelEntry 17 }                                               
                                                                                
     ibmMvsAtmOsasfChannelTime        OBJECT-TYPE                               
     SYNTAX  DisplayString (SIZE(0..8))                                         
     MAX-ACCESS read-only                                                       
     STATUS current                                                             
     DESCRIPTION                                                                
           "Time on this channel (set to 'NOTVALID' if there                    
            the disk serving function is not active)."                          
     ::= { osasfChannelEntry 18 }                                               
                                                                                
     ibmMvsAtmOsasfChannelFlashLevel OBJECT-TYPE                                
     SYNTAX  DisplayString (SIZE(1..32))                                        
     MAX-ACCESS read-only                                                       
     STATUS current                                                             
     DESCRIPTION                                                                
            "Flashlevel is the LAN driver level running on an OSA card.         
             For OSA1 and OSA2, there is only 1 LAN driver.                     
             For OSA2-ATM, you can have up to 2 LAN driver.                     
             The first driver if configured is for SNA and the second           
             driver is for ATM LAN. FlashLevel consists of two 16               
             OCTET fields, one for each LAN driver.                             
             FOR example, S:05:20:A0  for SNA &                                 
                            A:05.60.00  for ATM"                                
     ::= { osasfChannelEntry 19 }                                               
                                                                                
     ibmMvsAtmOsasfChannelVtamId OBJECT-TYPE                                    
     SYNTAX  Integer32                                                          
     MAX-ACCESS read-only                                                       
     STATUS current                                                             
     DESCRIPTION                                                                
           "VTAM ID if in SNA mode"                                             
     ::= { osasfChannelEntry 20 }                                               
                                                                                
     osasfPortTable OBJECT-TYPE                                                 
     SYNTAX SEQUENCE OF OsasfPortEntry                                          
     MAX-ACCESS not-accessible                                                  
     STATUS current                                                             
     DESCRIPTION                                                                
        "This table is intended to represent the ports supported                
         (or associated) with the osasfChannelTable entries. Each               
         OSA Channel has one or more OSA Ports.  For an ATM OSA2                
         device configured for ATM IP Forwarding mode, the following            
         fields do not apply:                                                   
             - ibmMvsAtmOsasfPortMacAddrBurntIn                                 
             - ibmMvsAtmOsasfPortMacAddrActive                                  
             - ibmMvsAtmOsasfPortMaxPcmConnections                              
             - ibmMvsAtmOsasfPortPcmName  "                                     
     ::= { ibmTcpipMvsAtmGroup 2 }                                              
                                                                                
     osasfPortEntry OBJECT-TYPE                                                 
     SYNTAX OsasfPortEntry                                                      
     MAX-ACCESS not-accessible                                                  
     STATUS current                                                             
     DESCRIPTION                                                                
        "Describes a particular OSA port entry, index by                        
         corresponding AAL5 entry's ifIndex."                                   
     INDEX { ifIndex }                                                          
     ::= { osasfPortTable 1 }                                                   
                                                                                
     OsasfPortEntry ::=                                                         
     SEQUENCE                                                                   
       {                                                                        
       ibmMvsAtmOsasfPortNumber                  Integer32,                     
       ibmMvsAtmOsasfPortType                     INTEGER,                      
       ibmMvsAtmOsasfPortHardwareState           INTEGER,                       
       ibmMvsAtmOsasfPortMediaType               INTEGER,                       
       ibmMvsAtmOsasfPortUniType                  INTEGER,                      
       ibmMvsAtmOsasfPortUniVersion               INTEGER,                      
       ibmMvsAtmOsasfPortNetPrefix               Integer32,                     
       ibmMvsAtmOsasfPortNetPrefixPrefix         OCTET STRING (SIZE(13)),       
       ibmMvsAtmOsasfPortNetPrefixStatus          INTEGER,                      
       ibmMvsAtmOsasfPortCodeLoadStatus          INTEGER,                       
       ibmMvsAtmOsasfPortMacAddrBurntIn          OCTET STRING (SIZE(6)),        
       ibmMvsAtmOsasfPortMacAddrActive           OCTET STRING (SIZE(6)),        
       ibmMvsAtmOsasfPortMaxPcmConnections       Integer32,                     
       ibmMvsAtmOsasfPortPcmName                 DisplayString,                 
       ibmMvsAtmOsasfPortAAL5InPackets           Counter32,                     
       ibmMvsAtmOsasfPortAAL5OutPackets          Counter32,                     
       ibmMvsAtmOsasfPortIpAddress               IpAddress                      
       }                                                                        
                                                                                
     ibmMvsAtmOsasfPortNumber        OBJECT-TYPE                                
     SYNTAX  Integer32                                                          
     MAX-ACCESS read-only                                                       
     STATUS current                                                             
     DESCRIPTION                                                                
           "Port number, starts at 0."                                          
     ::= { osasfPortEntry 1 }                                                   
                                                                                
     ibmMvsAtmOsasfPortType          OBJECT-TYPE                                
     SYNTAX  INTEGER { ethernet(1), tokenRing(2),                               
                        atm(9) }                                                
     MAX-ACCESS read-only                                                       
     STATUS current                                                             
     DESCRIPTION                                                                
           "The value of this object when the port is configured                
            to support atm natice traffic is atm(9). If configured              
            to run ATM LAN Emuliated than the value will be                     
            be either either ethernet(1) and/or tokenRing(2).                   
            Note that when a port is configured to be running                   
            ATM SNA LAN Emulation than up to two logical                        
            ATM SNA LE port entities may exist with any combination             
            of ethernet or tokenring port types."                               
     ::= { osasfPortEntry 2 }                                                   
                                                                                
     ibmMvsAtmOsasfPortHardwareState  OBJECT-TYPE                               
     SYNTAX  INTEGER {                                                          
                            enabled(0),                                         
                            hostDisabled(1),                                    
                            externallyDisabled(2),                              
                            internallyDisabled(3),                              
                            secmHostDisabled(4),                                
                            secmExternallyDisabled(5),                          
                            secmInternallyDisabled(6)                           
                          }                                                     
     MAX-ACCESS read-only                                                       
     STATUS current                                                             
     DESCRIPTION                                                                
           "The hardware state value ranges from 0 to 6 as follows:             
            0 - enable                                                          
            1 - disabled from host                                              
            2 - disabled from external source                                   
            3 - disabled from internal error                                    
            4 - service element control mode/disabled from host                 
            5 - service element control mode/disabled from external source      
            6 - service element control mode/disabled from internal error       
                                                                                
           where Host - OSA/SF or other host programming product                
              external source - human intervention on the service element"      
     ::= { osasfPortEntry 3 }                                                   
                                                                                
     ibmMvsAtmOsasfPortMediaType     OBJECT-TYPE                                
     SYNTAX  INTEGER { coaxCable(1), singleModeFiber(2),                        
                        multimodeFiber(3), shieldedTwistedPair(4),              
                        unshieldedTwistedPair(5) }                              
     MAX-ACCESS read-only                                                       
     STATUS current                                                             
     DESCRIPTION                                                                
           "ILMI atmfPortMediaType equivalent. OSA supports types               
            2 and 3"                                                            
     ::= { osasfPortEntry 4 }                                                   
                                                                                
     ibmMvsAtmOsasfPortUniType        OBJECT-TYPE                               
     SYNTAX  INTEGER { public(1), private(2) }                                  
     MAX-ACCESS read-only                                                       
     STATUS current                                                             
     DESCRIPTION                                                                
           "ILMI atmfAtmLayerUniType. OSA supports only 2"                      
     ::= { osasfPortEntry 5 }                                                   
                                                                                
     ibmMvsAtmOsasfPortUniVersion     OBJECT-TYPE                               
     SYNTAX  INTEGER { version20(1), version30(2), version31(3) }               
     MAX-ACCESS read-only                                                       
     STATUS current                                                             
     DESCRIPTION                                                                
           "ILMI atmfAtmLayerUniVersion. OSA supports only 3.                   
            This is the highest UNI version supported."                         
     ::= { osasfPortEntry 6 }                                                   
                                                                                
     ibmMvsAtmOsasfPortNetPrefix      OBJECT-TYPE                               
     SYNTAX  Integer32                                                          
     MAX-ACCESS read-only                                                       
     STATUS current                                                             
     DESCRIPTION                                                                
           "A unique value which identifies the UNI port for which              
            the network prefix for ATM addresses is in effect. The              
            value of 0 has the special meaning of identifying the               
            local UNI. OSA currently supports only 0."                          
     ::= { osasfPortEntry 7 }                                                   
                                                                                
     ibmMvsAtmOsasfPortNetPrefixPrefix OBJECT-TYPE                              
     SYNTAX  OCTET STRING (SIZE(13))                                            
     MAX-ACCESS read-only                                                       
     STATUS current                                                             
     DESCRIPTION                                                                
           "The network prefix for ATM addresses which is in effect             
            on the user-side of the ATM UNIT port. Network prefix is            
            defined as the ATM address, not including the ESA and               
            SEL portions. The meaningful portion of the OCTET STRING            
            is size 8 if it is E.164, 13 if private. In the case                
             of E.164 the remaining 5 octets are padded with zeros."            
     ::= { osasfPortEntry 8 }                                                   
                                                                                
     ibmMvsAtmOsasfPortNetPrefixStatus OBJECT-TYPE                              
     SYNTAX  INTEGER { valid(1), invalid(2) }                                   
     MAX-ACCESS read-only                                                       
     STATUS current                                                             
     DESCRIPTION                                                                
           "Equivalent to the atmfNetPrefixStatus as defined in                 
            the Network Prefix Table in the ILMI Address Registration           
            MIB. An indication of the validity of the network prefix            
            for ATM addresses on the user-side of the UNI port."                
     ::= { osasfPortEntry 9 }                                                   
                                                                                
     ibmMvsAtmOsasfPortCodeLoadStatus  OBJECT-TYPE                              
     SYNTAX  INTEGER { operational(1), notOperational(2),                       
                        configRejected(3), outOfSync(4) }                       
     MAX-ACCESS read-only                                                       
     STATUS current                                                             
     DESCRIPTION                                                                
           "This object specifies whether the ATM code has been loaded          
            on to the adapter. The configRejected state indicates               
            that the ATM configuration file download via OSA/SF has             
            been found to be incorrect. The outOfSync condition                 
            indicates that the OSA firmware and the ATM code both               
            running on the OSA have been found to be at incompatible            
            levels. Any state other than operational infers that                
            the data associated with a port may be incorrect.                   
            Note: OSA/SF should only report states operational                  
            and notoperational."                                                
     ::= { osasfPortEntry 10 }                                                  
                                                                                
     ibmMvsAtmOsasfPortMacAddrBurntIn  OBJECT-TYPE                              
     SYNTAX  OCTET STRING (SIZE(6))                                             
     MAX-ACCESS read-only                                                       
     STATUS current                                                             
     DESCRIPTION                                                                
           "A 6 byte OCTET STRING which contains the adapter's                  
            burned in MAC address.  Does not apply to ATM OSA2                  
            device configured for ATM IP Forwarding mode."                      
     ::= { osasfPortEntry 11 }                                                  
                                                                                
     ibmMvsAtmOsasfPortMacAddrActive   OBJECT-TYPE                              
     SYNTAX  OCTET STRING (SIZE(6))                                             
     MAX-ACCESS read-only                                                       
     STATUS current                                                             
     DESCRIPTION                                                                
           "A 6 byte OCTET STRING which contains the current                    
            MAC address in use on the adapter.  Does not apply to               
            ATM OSA2 device configured for ATM IP Forwarding mode."             
     ::= { osasfPortEntry 12 }                                                  
                                                                                
     ibmMvsAtmOsasfPortMaxPcmConnections   OBJECT-TYPE                          
     SYNTAX  Integer32                                                          
     MAX-ACCESS read-only                                                       
     STATUS current                                                             
     DESCRIPTION                                                                
           "Specifies the maximum number of connects on an OSA port             
            which can be used for ATM exploitation purposes. It can             
            range from 0 to the number specified by                             
            atmInterfaceMaxVccs (RFC 1695). A 0 indicates either that           
            the connections on this port are being used by an ATM OSA2          
            configured for LAN Emulation or ATM IP Forwarding.                  
            If the value specified here is the same                             
            as what is specified by atmInterfaceMaxVccs then all                
            connections are allocated to ATM exploitation."                     
     ::= { osasfPortEntry 13 }                                                  
                                                                                
     ibmMvsAtmOsasfPortPcmName       OBJECT-TYPE                                
     SYNTAX  DisplayString (SIZE(1..16))                                        
     MAX-ACCESS read-only                                                       
     STATUS current                                                             
     DESCRIPTION                                                                
           "Specifies the Port Name which must also be entered at the           
            connection manager on the host and the application. Port            
            Name is specifed to OSA/SF as a config file parameter               
            (PCM_NAME). This value is also specified via ILMI as                
            the value of the atmfPortMyIfName object.  Does not                 
            apply to an ATM OSA2 device configured for                          
            ATM IP Forwarding mode."                                            
     ::= { osasfPortEntry 14 }                                                  
                                                                                
     ibmMvsAtmOsasfPortAAL5InPackets OBJECT-TYPE                                
     SYNTAX  Counter32                                                          
     MAX-ACCESS read-only                                                       
     STATUS current                                                             
     DESCRIPTION                                                                
           "inbound packets at the corresponding AAL5 interface layer."         
     ::= { osasfPortEntry 15 }                                                  
                                                                                
     ibmMvsAtmOsasfPortAAL5OutPackets OBJECT-TYPE                               
     SYNTAX  Counter32                                                          
     MAX-ACCESS read-only                                                       
     STATUS current                                                             
     DESCRIPTION                                                                
           "outbound packets at the corresponding AAL5 interface layer."        
     ::= { osasfPortEntry 16 }                                                  
                                                                                
     ibmMvsAtmOsasfPortIpAddress      OBJECT-TYPE                               
     SYNTAX  IpAddress                                                          
     MAX-ACCESS  read-write                                                     
     STATUS  current                                                            
     DESCRIPTION                                                                
             "The managing IpAddress reported by the ATM port as                
             its atmfMyIpNmAddress as specified by the ATM Forum                
             User-NetworkInterface (UNI) specification."                        
     ::= { osasfPortEntry 17 }                                                  
                                                                                
     osasfPvcTable OBJECT-TYPE                                                  
     SYNTAX SEQUENCE OF OsasfPvcEntry                                           
     MAX-ACCESS not-accessible                                                  
     STATUS current                                                             
     DESCRIPTION                                                                
        "This table is intended to represent the locally                        
         configured PVCs associated with a given OSA Port.                      
         There is a limit of 128 PVCs per PORT per Channel."                    
     ::= { ibmTcpipMvsAtmGroup 3 }                                              
                                                                                
     osasfPvcEntry OBJECT-TYPE                                                  
     SYNTAX OsasfPvcEntry                                                       
     MAX-ACCESS not-accessible                                                  
     STATUS current                                                             
     DESCRIPTION                                                                
        "This object is intended to represent a single PVC                      
         entry for the osasfPvcTable."                                          
     INDEX { ifIndex, ibmMvsAtmOsasfPvcName }                                   
     ::= { osasfPvcTable 1 }                                                    
                                                                                
     OsasfPvcEntry ::=                                                          
     SEQUENCE                                                                   
       {                                                                        
       ibmMvsAtmOsasfPvcName               DisplayString,                       
       ibmMvsAtmOsasfPvcBestEffort         Integer32,                           
       ibmMvsAtmOsasfPvcFwdPeakCellRate    Integer32,                           
       ibmMvsAtmOsasfPvcBwdPeakCellRate    Integer32,                           
       ibmMvsAtmOsasfPvcFwdsustainCellRate Integer32,                           
       ibmMvsAtmOsasfPvcBwdsustainCellRate Integer32,                           
       ibmMvsAtmOsasfPvcFwdCellBurstSize   Integer32,                           
       ibmMvsAtmOsasfPvcBwdCellBurstSize   Integer32,                           
       ibmMvsAtmOsasfPvcVpi                Integer32,                           
       ibmMvsAtmOsasfPvcVci                Integer32,                           
       ibmMvsAtmOsasfPvcFwdMaxAal5PduSize  INTEGER,                             
       ibmMvsAtmOsasfPvcBwdMaxAal5PduSize  INTEGER                              
       }                                                                        
                                                                                
     ibmMvsAtmOsasfPvcName            OBJECT-TYPE                               
     SYNTAX  DisplayString (SIZE(1..8))                                         
     MAX-ACCESS read-only                                                       
     STATUS current                                                             
     DESCRIPTION                                                                
           "PVC Name"                                                           
     ::= { osasfPvcEntry 1 }                                                    
                                                                                
     ibmMvsAtmOsasfPvcBestEffort         OBJECT-TYPE                            
     SYNTAX  Integer32 ( 0..1 )                                                 
     MAX-ACCESS read-only                                                       
     STATUS current                                                             
     DESCRIPTION                                                                
           "Best Effort rate. 0 indicated that best effort                      
            delivery is not desired. 1 indicates that best                      
            effort delivery is desired."                                        
     ::= { osasfPvcEntry 2 }                                                    
                                                                                
     ibmMvsAtmOsasfPvcFwdPeakCellRate    OBJECT-TYPE                            
     SYNTAX  Integer32                                                          
     MAX-ACCESS read-only                                                       
     STATUS current                                                             
     DESCRIPTION                                                                
           "Forward peak cell rate specified as cells per second.               
            Needed in order to set up either a best effort or                   
            a reserved bandwidth PVC. It applies to the outbound                
            direction (OSA to network) and specifies an upper bound             
            on the outbound traffic that can be transmitted on this             
            PVC. This value can not exceed the the link speed of                
            the ATM link."                                                      
     ::= { osasfPvcEntry 3 }                                                    
                                                                                
     ibmMvsAtmOsasfPvcBwdPeakCellRate    OBJECT-TYPE                            
     SYNTAX  Integer32                                                          
     MAX-ACCESS read-only                                                       
     STATUS current                                                             
     DESCRIPTION                                                                
           "Backward peak cell rate specified as cells per second.              
            Needed in order to set up either a best effort or                   
            a reserved bandwidth PVC. It applies to the inbound                 
            direction (network to OSA) and specifies an upper bound             
            on the inbound traffic that can be received on this                 
            PVC. This value can not exceed the the link speed of                
            the ATM link."                                                      
     ::= { osasfPvcEntry 4 }                                                    
                                                                                
     ibmMvsAtmOsasfPvcFwdsustainCellRate OBJECT-TYPE                            
     SYNTAX  Integer32                                                          
     MAX-ACCESS read-only                                                       
     STATUS current                                                             
     DESCRIPTION                                                                
           "Forward sustain cell rate specified as cells per second.            
            If the best effort indicator is on, the value of this               
            object is ignored. Otherwise (for a reserved bandwidth              
            PVC) this value is utilized by OSA. A value of 0xFF                 
            indicates that this value is not being used.                        
            Forward sustain cell rate specifies the desired cell rate           
            for outbound traffic that can be sustained for life of              
            a connection on this PVC. This value can not exceed the             
            ATM ports link speed."                                              
     ::= { osasfPvcEntry 5 }                                                    
                                                                                
     ibmMvsAtmOsasfPvcBwdsustainCellRate OBJECT-TYPE                            
     SYNTAX  Integer32                                                          
     MAX-ACCESS read-only                                                       
     STATUS current                                                             
     DESCRIPTION                                                                
           "Backward sustain cell rate specified as cells per second.           
            If the best effort indicator is on, the value of this               
            object is ignored. Otherwise (for a reserved bandwidth              
            PVC) this value is utilized by OSA. A value of 0xFF                 
            indicates that this value is not being used.                        
            Backward sustain cell rate specifies the desired cell rate          
            for inbound traffic that can be sustained for life of               
            a connection on this PVC. This value can not exceed the             
            ATM ports link speed."                                              
     ::= { osasfPvcEntry 6 }                                                    
                                                                                
     ibmMvsAtmOsasfPvcFwdCellBurstSize   OBJECT-TYPE                            
     SYNTAX  Integer32                                                          
     MAX-ACCESS read-only                                                       
     STATUS current                                                             
     DESCRIPTION                                                                
           "Forward cell burst size specified as number of cells.               
            If the best effort indicator is on, the value of this               
            object is ignored. Otherwise (for a reserved bandwidth              
            PVC) this value is utilized by OSA. A value of 0xFF                 
            indicates that this value is not being used.                        
            Forward cell burst size specifies the maximum number of             
            cells that can be transmitted in the outbound direction at          
            the peak cell rate while maintaining conformance to the             
            PVC traffic contract."                                              
     ::= { osasfPvcEntry 7 }                                                    
                                                                                
     ibmMvsAtmOsasfPvcBwdCellBurstSize   OBJECT-TYPE                            
     SYNTAX  Integer32                                                          
     MAX-ACCESS read-only                                                       
     STATUS current                                                             
     DESCRIPTION                                                                
           "Backward cell burst size specified as number of cells.              
            If the best effort indicator is on, the value of this               
            object is ignored. Otherwise (for a reserved bandwidth              
            PVC) this value is utilized by OSA. A value of 0xFF                 
            indicates that this value is not being used.                        
            Backward cell burst size specifies the maximum number of            
            cells that can be received in the inbound direction at              
            the peak cell rate while maintaining conformance to the             
            PVC traffic contract."                                              
     ::= { osasfPvcEntry 8 }                                                    
                                                                                
     ibmMvsAtmOsasfPvcVpi      OBJECT-TYPE                                      
     SYNTAX  Integer32                                                          
     MAX-ACCESS read-only                                                       
     STATUS current                                                             
     DESCRIPTION                                                                
           "vpi for this PVC"                                                   
     ::= { osasfPvcEntry 9 }                                                    
                                                                                
     ibmMvsAtmOsasfPvcVci      OBJECT-TYPE                                      
     SYNTAX  Integer32                                                          
     MAX-ACCESS read-only                                                       
     STATUS current                                                             
     DESCRIPTION                                                                
           "vci for this PVC. This value must be greater than or                
            equal to 32 since the first 32 vci code points have                 
            been reserved by the ATM Forum."                                    
     ::= { osasfPvcEntry 10 }                                                   
                                                                                
     ibmMvsAtmOsasfPvcFwdMaxAal5PduSize  OBJECT-TYPE                            
     SYNTAX  INTEGER (64..9188)                                                 
     MAX-ACCESS read-only                                                       
     STATUS current                                                             
     DESCRIPTION                                                                
           "This field is used to setup the PVC. Units are in                   
            OCTETs and represents the largest PDU size for the                  
            AAL5 CPCS layer that can be processed in the forward                
            direction for this PVC by the AAL5 entity. For best                 
            effort PVCs only, OSA/SF should attempt to default the              
            value to the largest size (9188)."                                  
     ::= { osasfPvcEntry 11 }                                                   
                                                                                
     ibmMvsAtmOsasfPvcBwdMaxAal5PduSize  OBJECT-TYPE                            
     SYNTAX  INTEGER (64..9188)                                                 
     MAX-ACCESS read-only                                                       
     STATUS current                                                             
     DESCRIPTION                                                                
           "This field is used to setup the PVC. Units are in                   
            OCTETs and represents the largest PDU size for the                  
            AAL5 CPCS layer that can be processed in the backward               
            direction for this PVC by the AAL5 entity. For best                 
            effort PVCs only, OSA/SF should attempt to default the              
            value to the largest size (9188)."                                  
     ::= { osasfPvcEntry 12 }                                                   
                                                                                
     ibmMvsAtmSnaLeTable OBJECT-TYPE                                            
     SYNTAX SEQUENCE OF IbmMvsAtmSnaLeEntry                                     
     MAX-ACCESS not-accessible                                                  
     STATUS current                                                             
     DESCRIPTION                                                                
        "This table is intended to represent the data that is                   
         available from an OSA Port that is running SNA LAN                     
         Emulation mode. An entry in this table is indexed by                   
         a LAN Emulation ifIndex"                                               
     ::= { ibmTcpipMvsAtmGroup 4 }                                              
                                                                                
     ibmMvsAtmSnaLeEntry OBJECT-TYPE                                            
     SYNTAX IbmMvsAtmSnaLeEntry                                                 
     MAX-ACCESS not-accessible                                                  
     STATUS current                                                             
     DESCRIPTION                                                                
        "Describes a particular OSA SNA LAN Emulation entry, index by           
         corresponding LAN Emulation ifIndex."                                  
     INDEX { ifIndex }                                                          
     ::= { ibmMvsAtmSnaLeTable 1 }                                              
                                                                                
     IbmMvsAtmSnaLeEntry ::=                                                    
     SEQUENCE                                                                   
       {                                                                        
         ibmMvsAtmSnaLeLlcTi                Integer32,                          
         ibmMvsAtmSnaLeLlcT1                Integer32,                          
         ibmMvsAtmSnaLeLlcT2                Integer32,                          
         ibmMvsAtmSnaleMaxStations          Integer32,                          
         ibmMvsAtmSnaLeMaxSaps              Integer32,                          
         ibmMvsAtmSnaleMaxIn                Integer32,                          
         ibmMvsAtmSnaLeMaxOut               Integer32,                          
         ibmMvsAtmSnaLeCrsGroupAddress      OCTET STRING,                       
         ibmMvsAtmSnaLeUserData             OCTET STRING,                       
         ibmMvsAtmSnaLeClientEnableState      INTEGER,                          
         ibmMvsAtmSnaLeBestEffortPeakRate   Integer32,                          
         ibmMvsAtmSnaLeMaxLECConnections    Integer32,                          
         ibmMvsAtmSnaLeTrEnableLoadBalancing INTEGER,                           
         ibmMvsAtmSnaLeTrLoadBalancing        INTEGER,                          
         ibmMvsAtmSnaLeTrSessionDelay         INTEGER                           
       }                                                                        
                                                                                
     ibmMvsAtmSnaLeLlcTi  OBJECT-TYPE                                           
     SYNTAX  Integer32 (1..255)                                                 
     MAX-ACCESS read-only                                                       
     STATUS current                                                             
     DESCRIPTION                                                                
           ""                                                                   
     ::= { ibmMvsAtmSnaLeEntry 1 }                                              
                                                                                
     ibmMvsAtmSnaLeLlcT1 OBJECT-TYPE                                            
     SYNTAX  Integer32 (1..255)                                                 
     MAX-ACCESS read-only                                                       
     STATUS current                                                             
     DESCRIPTION                                                                
           ""                                                                   
     ::= { ibmMvsAtmSnaLeEntry 2 }                                              
                                                                                
     ibmMvsAtmSnaLeLlcT2 OBJECT-TYPE                                            
     SYNTAX  Integer32 (1..255)                                                 
     MAX-ACCESS read-only                                                       
     STATUS current                                                             
     DESCRIPTION                                                                
           ""                                                                   
     ::= { ibmMvsAtmSnaLeEntry 3 }                                              
                                                                                
     ibmMvsAtmSnaleMaxStations  OBJECT-TYPE                                     
     SYNTAX  Integer32 (1..255)                                                 
     MAX-ACCESS read-only                                                       
     STATUS current                                                             
     DESCRIPTION                                                                
           ""                                                                   
     ::= { ibmMvsAtmSnaLeEntry 4 }                                              
                                                                                
     ibmMvsAtmSnaLeMaxSaps  OBJECT-TYPE                                         
     SYNTAX  Integer32 (1..127)                                                 
     MAX-ACCESS read-only                                                       
     STATUS current                                                             
     DESCRIPTION                                                                
           ""                                                                   
     ::= { ibmMvsAtmSnaLeEntry 5 }                                              
                                                                                
     ibmMvsAtmSnaleMaxIn OBJECT-TYPE                                            
     SYNTAX  Integer32 (1..127)                                                 
     MAX-ACCESS read-only                                                       
     STATUS current                                                             
     DESCRIPTION                                                                
           ""                                                                   
     ::= { ibmMvsAtmSnaLeEntry 6 }                                              
                                                                                
     ibmMvsAtmSnaLeMaxOut OBJECT-TYPE                                           
     SYNTAX  Integer32 (1..127)                                                 
     MAX-ACCESS read-only                                                       
     STATUS current                                                             
     DESCRIPTION                                                                
           ""                                                                   
     ::= { ibmMvsAtmSnaLeEntry 7 }                                              
                                                                                
     ibmMvsAtmSnaLeCrsGroupAddress OBJECT-TYPE                                  
     SYNTAX  OCTET STRING(SIZE(256))                                            
     MAX-ACCESS read-only                                                       
     STATUS current                                                             
     DESCRIPTION                                                                
            "This field contains the active Group Addresses.                    
             An individual Group Address is 6 bytes long.                       
             Therefore, this field is actually 32 times                         
             (OCTET STRING(SIZE(6)) + 2 bytes of padding) long."                
     ::= { ibmMvsAtmSnaLeEntry 8 }                                              
                                                                                
     ibmMvsAtmSnaLeUserData  OBJECT-TYPE                                        
     SYNTAX  OCTET STRING (SIZE(32))                                            
     MAX-ACCESS read-only                                                       
     STATUS current                                                             
     DESCRIPTION                                                                
            "This field contains a character string of user                     
             data that can be used to further describe this port."              
     ::= { ibmMvsAtmSnaLeEntry 9 }                                              
                                                                                
     ibmMvsAtmSnaLeClientEnableState  OBJECT-TYPE                               
     SYNTAX  INTEGER {                                                          
                          notDefined(1),                                        
                          lecActivating(2),                                     
                          enabled(3),                                           
                          internalFailureDisabled(4),                           
                          physicalPortDisabled(5),                              
                          osasfDisabled(6),                                     
                          externalDisabled(7),                                  
                          unknown(8)                                            
                       }                                                        
     MAX-ACCESS read-only                                                       
     STATUS current                                                             
     DESCRIPTION                                                                
           "This object describes the state of the specified LAN                
            Emulation Port. notDefined implies that the port is                 
            not defined in the configuration file. lecActivating                
            indicates the port is in the process of being enabled.              
            There are for possible reasons that the port could be               
            diabled as implied by the enumeration list."                        
     ::= { ibmMvsAtmSnaLeEntry 10 }                                             
                                                                                
     ibmMvsAtmSnaLeBestEffortPeakRate OBJECT-TYPE                               
     SYNTAX  Integer32                                                          
     MAX-ACCESS read-only                                                       
     STATUS current                                                             
     DESCRIPTION                                                                
           "This object is the signaling parameter that should                  
            be used by the LEC when setting up all best effort VCCs.            
            This parameter applies to the forward and backward                  
            direction on a per best effort VCC basis. Thus a 155 Mb             
            card may be configured to send best effort traffic at               
            25.6 Mb (per VCC), but with a total card bandwidth of               
            up to 155 Mb. Since this parameter has an integer value             
            the unis are 10xMbits/sec."                                         
     ::= { ibmMvsAtmSnaLeEntry 11 }                                             
                                                                                
     ibmMvsAtmSnaLeMaxLECConnections  OBJECT-TYPE                               
     SYNTAX  Integer32 (1..65536)                                               
     MAX-ACCESS read-only                                                       
     STATUS current                                                             
     DESCRIPTION                                                                
           "This object specifies the maximum number of connections             
            on an OSA port which can be used for LAN Emulation                  
            purposes. It can range from 0 to the number specified               
            by atmInterfaceMaxVccs. 0 would indicate that the                   
            connections on this port are only being used by ATM                 
            Exploitation. If the value of this parameter was equal              
            to atmInterfaceMaxVccs then all connections are allocated           
            to LAN Emulation.  Note that this number is the same for            
            all LECs. It is NOT defined on a per LEC basis."                    
     ::= { ibmMvsAtmSnaLeEntry 12 }                                             
                                                                                
    ibmMvsAtmSnaLeTrEnableLoadBalancing OBJECT-TYPE                             
    SYNTAX  INTEGER (0..1)                                                      
    MAX-ACCESS read-only                                                        
    STATUS current                                                              
    DESCRIPTION                                                                 
          ""                                                                    
    ::= { ibmMvsAtmSnaLeEntry 13 }                                              
                                                                                
    ibmMvsAtmSnaLeTrLoadBalancing  OBJECT-TYPE                                  
    SYNTAX  INTEGER (0..25)                                                     
    MAX-ACCESS read-only                                                        
    STATUS current                                                              
    DESCRIPTION                                                                 
          ""                                                                    
    ::= { ibmMvsAtmSnaLeEntry 14 }                                              
                                                                                
    ibmMvsAtmSnaLeTrSessionDelay OBJECT-TYPE                                    
    SYNTAX  INTEGER (0..375)                                                    
    MAX-ACCESS read-only                                                        
    STATUS current                                                              
    DESCRIPTION                                                                 
          ""                                                                    
    ::= { ibmMvsAtmSnaLeEntry 15 }                                              
                                                                                
                                                                                
     ibmMvsAtmLecConfigTable OBJECT-TYPE                                        
     SYNTAX SEQUENCE OF IbmMvsAtmLecConfigEntry                                 
     MAX-ACCESS not-accessible                                                  
     STATUS current                                                             
     DESCRIPTION                                                                
        "This table is intended to represent the data that is                   
         available from an OSA Port that is running SNA LAN                     
         Emulation mode. An entry in this table is indexed a SNA                
         LAN Emulation ifIndex. Am ifEntry who's ifType is either               
         aflane802.3 (59) or aflane802.5 (60) will have a                       
         corresponding entry in this table. This table is modeled               
         after the LEC Config Table from the LAN Emulation MIB                  
         defined by the ATM Forum."                                             
     ::= { ibmTcpipMvsAtmGroup 5 }                                              
                                                                                
     ibmMvsAtmLecConfigEntry OBJECT-TYPE                                        
     SYNTAX IbmMvsAtmLecConfigEntry                                             
     MAX-ACCESS not-accessible                                                  
     STATUS current                                                             
     DESCRIPTION                                                                
        "Describes a particular ATM Lec Config Table entry, index by            
         either a aflan802.3 or a aflane802.5 ifEntry's ifIndex."               
     INDEX { ifIndex }                                                          
     ::= { ibmMvsAtmLecConfigTable 1 }                                          
                                                                                
     IbmMvsAtmLecConfigEntry ::=                                                
     SEQUENCE                                                                   
       {                                                                        
         ibmMvsAtmLecConfigMode              INTEGER,                           
         ibmMvsAtmLecConfigLanType           INTEGER,                           
         ibmMvsAtmLecConfigMaxDataFrameSize  INTEGER,                           
         ibmMvsAtmLecConfigLanName           OCTET STRING (SIZE(32)),           
         ibmMvsAtmLecConfigLesAtmAddress     OCTET STRING (SIZE(20)),           
         ibmMvsAtmLecControlTimeout          Integer32,                         
         ibmMvsAtmLecMaxUnknownFrameCount    Integer32,                         
         ibmMvsAtmLecMaxUnknownFrameTime     Integer32,                         
         ibmMvsAtmLecVccTimeoutPeriod        Integer32,                         
         ibmMvsAtmLecMaxRetryCount           Integer32,                         
         ibmMvsAtmLecAgingTime               Integer32,                         
         ibmMvsAtmLecForwardDelayTime        Integer32,                         
         ibmMvsAtmLecExpectedArpResponseTime Integer32,                         
         ibmMvsAtmLecFlushTimeout            Integer32,                         
         ibmMvsAtmLecPathSwitchingDelay      Integer32,                         
         ibmMvsAtmLecLocalSegmentID          Integer32,                         
         ibmMvsAtmLecMulticastSendType       INTEGER,                           
         ibmMvsAtmLecMulticastSendAvgRate    Integer32,                         
         ibmMvsAtmLecMulticastSendPeakRate   Integer32,                         
         ibmMvsAtmLecConnectionCompleteTimer Integer32                          
       }                                                                        
                                                                                
     ibmMvsAtmLecConfigMode   OBJECT-TYPE                                       
     SYNTAX  INTEGER { automatic(1), manual(2) }                                
     MAX-ACCESS read-only                                                       
     STATUS current                                                             
     DESCRIPTION                                                                
           "Indicates whether thus LAN Emulation Client should                  
            auto-configure the next time it is (re)started. In                  
            automatic (1) mode, a client uses a LAN Emulation                   
            Configuration Server to learn the ATM address of its                
            LAN Emulation Server, and to obtain other parameters.               
            lecConfig (LanType, MaxDataFrameSize, LanName) are                  
            used in the configure request. lecConfigLesAtmAddress               
            is ignored. In manual (2) mode, management tells the                
            client the ATM address of its LAN Emulation Server                  
            and the value of the other parmeters. lecConfig                     
            (LanType, MaxDataFrameSize, LanName) are used in the                
            Join request. lecConfigLesAtmAddress tells the client               
            which LES to call."                                                 
     ::= { ibmMvsAtmLecConfigEntry 1 }                                          
                                                                                
     ibmMvsAtmLecConfigLanType   OBJECT-TYPE                                    
     SYNTAX  INTEGER { unspecified (1), ethernet(2), tokenRing(3) }             
     MAX-ACCESS read-only                                                       
     STATUS current                                                             
     DESCRIPTION                                                                
           "The data frame format which this client will use                    
            the next time it returns to the Initial State.                      
            Auto-configuring clients use this parameter in their                
            configure requests. Manually configured clients use                 
            it in their joint requests."                                        
     ::= { ibmMvsAtmLecConfigEntry 2 }                                          
                                                                                
     ibmMvsAtmLecConfigMaxDataFrameSize  OBJECT-TYPE                            
     SYNTAX  INTEGER {                                                          
                         unspecified (1),                                       
                         f1516 (2),                                             
                         f4544 (3),                                             
                         f9234 (4),                                             
                         f18190 (5)                                             
                       }                                                        
     MAX-ACCESS read-only                                                       
     STATUS current                                                             
     DESCRIPTION                                                                
           "The maximum data frame size (in bytes) which this                   
            client will use the next time it returns to the Initial             
            State. Auto-configuring clients use this parameter in               
            their configure requests. Manually configured clients use           
            it in their joint requests."                                        
     ::= { ibmMvsAtmLecConfigEntry 3 }                                          
                                                                                
     ibmMvsAtmLecConfigLanName   OBJECT-TYPE                                    
     SYNTAX   OCTET STRING (SIZE(32))                                           
     MAX-ACCESS read-only                                                       
     STATUS current                                                             
     DESCRIPTION                                                                
           "The ELAN Name this client will use the                              
            next time it returns to the Initial State.                          
            Auto-configuring clients use this parameter in                      
            their configure requests. Manually configured clients use           
            it in their joint requests."                                        
     ::= { ibmMvsAtmLecConfigEntry 4 }                                          
                                                                                
     ibmMvsAtmLecConfigLesAtmAddress     OBJECT-TYPE                            
     SYNTAX   OCTET STRING (SIZE(20))                                           
     MAX-ACCESS read-only                                                       
     STATUS current                                                             
     DESCRIPTION                                                                
          "The LAN Emulation Server which this client will use the              
           next time it is started in manual configuration mode.                
           When lecConfigMode is 'automatic', there is no need to set           
           this address, Address) and no advantage to doing so. The             
           client will use the LECS to find a LES, putting the                  
           auto-configured address in lecActualLesAtmAddress                    
           while leaving lecConfigLesAtmAddress alone. Corresponds to           
           Initial State Parameter C9. In LAN Emulation MIB, the                
           OCTET STRING has length 0 or 20. For OSA, the length shall           
           be 20, with  the value 0 defined to mean that                        
           lecConfigMode is 'automatic'."                                       
     ::= { ibmMvsAtmLecConfigEntry 5 }                                          
                                                                                
     ibmMvsAtmLecControlTimeout   OBJECT-TYPE                                   
     SYNTAX   Integer32 (10..300)                                               
     MAX-ACCESS read-only                                                       
     STATUS current                                                             
     DESCRIPTION                                                                
          "Control Time-out. Time out period used for timing out most           
           request/response control frame interactions, as specified            
           elsewhere in the LAN Emulation specification.                        
           This time value is expressed in seconds. Corresponds to              
           Initial State Parameter C7."                                         
     ::= { ibmMvsAtmLecConfigEntry 6 }                                          
                                                                                
     ibmMvsAtmLecMaxUnknownFrameCount OBJECT-TYPE                               
     SYNTAX   Integer32 (1..10)                                                 
     MAX-ACCESS read-only                                                       
     STATUS current                                                             
     DESCRIPTION                                                                
          "Maximum Unknown Frame Count. See the description of                  
           lecMaxUnknownFrameTime below. Corresponds to Initial                 
           State Parameter C10."                                                
     ::= { ibmMvsAtmLecConfigEntry 7 }                                          
                                                                                
     ibmMvsAtmLecMaxUnknownFrameTime  OBJECT-TYPE                               
     SYNTAX   Integer32 (1..60)                                                 
     MAX-ACCESS read-only                                                       
     STATUS current                                                             
     DESCRIPTION                                                                
          "Maximum Unknown Frame Time. Within the period of time                
           defined by the Maximum Unknown Frame Time, a LE Client               
           will send no more than Maximum Unknown Frame Count                   
           frames to the BUS for a given unicast LAN Destination,               
           and it must also initiate the address resolution                     
           protocol to resolve that LAN Destination. This time                  
           value is expressed in seconds. Corresponds Initial State             
           Parameter C11."                                                      
     ::= { ibmMvsAtmLecConfigEntry 8 }                                          
                                                                                
     ibmMvsAtmLecVccTimeoutPeriod  OBJECT-TYPE                                  
     SYNTAX   Integer32                                                         
     MAX-ACCESS read-only                                                       
     STATUS current                                                             
     DESCRIPTION                                                                
          "VCC Time-out Period. A LE Client SHOULD release any                  
           Data Direct VCC that it has not used to transmit                     
           or receive any data frames for the length of the VCC                 
           Time-out Period. This parameter is only meaningful for               
           SVC Data Direct VCCs.                                                
           This time value is expressed in seconds. The default                 
           value is 20 minutes. A value of 0 seconds means                      
           that the timeout period is infinite.                                 
           Negative values will be rejected by the agent.                       
           Corresponds to Initial State Parameter C12."                         
     ::= { ibmMvsAtmLecConfigEntry 9 }                                          
                                                                                
     ibmMvsAtmLecMaxRetryCount  OBJECT-TYPE                                     
     SYNTAX   Integer32 (0..2)                                                  
     MAX-ACCESS read-only                                                       
     STATUS current                                                             
     DESCRIPTION                                                                
          "Maximum Retry Count. A LE CLient MUST not retry a                    
           LE_ARP_REQUEST for a given frame's LAN destination                   
           more than Maximum Retry Count times, after the first                 
           LE_ARP_REQUEST for that same frame's LAN destination.                
           Corresponds to Initial State Parameter C13."                         
     ::= { ibmMvsAtmLecConfigEntry 10 }                                         
                                                                                
     ibmMvsAtmLecAgingTime  OBJECT-TYPE                                         
     SYNTAX   Integer32 (10..300)                                               
     MAX-ACCESS read-only                                                       
     STATUS current                                                             
     DESCRIPTION                                                                
          "Aging Time. The maximum time that a LE Client will                   
           maintain an entry in its LE_ARP cache in the absence                 
           of a verification of that relationship.                              
           This time value is expressed in seconds. Corresponds to              
           Initial State Parameter C17."                                        
     ::= { ibmMvsAtmLecConfigEntry 11 }                                         
                                                                                
     ibmMvsAtmLecForwardDelayTime  OBJECT-TYPE                                  
     SYNTAX   Integer32 (4..30)                                                 
     MAX-ACCESS read-only                                                       
     STATUS current                                                             
     DESCRIPTION                                                                
          "Forward Delay Time. The maximum time that a LE Client                
           will maintain an entry for a non-local MAC address in                
           its LE_ARP cache in the absence of a verification of                 
           that relationship, as long as the Topology Change flag               
           C19 is true. lecForwardDelayTime SHOULD BE less than                 
           lecAgingTime. When it is not, lecAgingTime governs LE_ARP            
           aging.                                                               
           This time value is expressed in seconds. Corresponds to              
           Initial State Parameter C18."                                        
     ::= { ibmMvsAtmLecConfigEntry 12 }                                         
                                                                                
     ibmMvsAtmLecExpectedArpResponseTime  OBJECT-TYPE                           
     SYNTAX   Integer32 (1..30)                                                 
     MAX-ACCESS read-only                                                       
     STATUS current                                                             
     DESCRIPTION                                                                
          "Expected LE_ARP Reponse Time. The maximum time that                  
           the LEC expects an LE_ARP_REQUEST/LE_ARP_RESPONSE                    
           cycle to take. Used for retries and verifies. This                   
           time value is expressed in Time) seconds. Corresponds                
           to Initial State Parameter C20."                                     
     ::= { ibmMvsAtmLecConfigEntry 13 }                                         
                                                                                
     ibmMvsAtmLecFlushTimeout OBJECT-TYPE                                       
     SYNTAX   Integer32 (1..4)                                                  
     MAX-ACCESS read-only                                                       
     STATUS current                                                             
     DESCRIPTION                                                                
          "Flush Time-out. Time limit to wait to receive a                      
           LE_FLUSH_RESPONSE after the LE_FLUSH_REQUEST has been                
           sent before taking recovery action. This time value                  
           is expressed in seconds. Corresponds to Initial State                
           Parameter C21."                                                      
     ::= { ibmMvsAtmLecConfigEntry 14 }                                         
                                                                                
     ibmMvsAtmLecPathSwitchingDelay  OBJECT-TYPE                                
     SYNTAX   Integer32 (1..8)                                                  
     MAX-ACCESS read-only                                                       
     STATUS current                                                             
     DESCRIPTION                                                                
          "Path Switching Delay. The time since sending a                       
           frame to the BUS after which the LE Client may                       
           assume that the frame has been either discarded                      
           or delivered to the recipient. May be used to                        
           bypass the Flush protocol. This time value is                        
           expressed in seconds. Corresponds to Initial State                   
           Parameter C22."                                                      
     ::= { ibmMvsAtmLecConfigEntry 15 }                                         
                                                                                
     ibmMvsAtmLecLocalSegmentID  OBJECT-TYPE                                    
     SYNTAX   Integer32 (0..4095)                                               
     MAX-ACCESS read-only                                                       
     STATUS current                                                             
     DESCRIPTION                                                                
          "Local Segment ID. The segment ID of the emulated LAN.                
           This is only required for IEEE 802.5 clients that                    
           are Source Routing bridges. Corresponds to Initial                   
           State Parameter C23."                                                
     ::= { ibmMvsAtmLecConfigEntry 16 }                                         
                                                                                
     ibmMvsAtmLecMulticastSendType  OBJECT-TYPE                                 
     SYNTAX   INTEGER {                                                         
                          bestEffort(1),                                        
                          variableBitRate(2),                                   
                          constantBitRate(3)                                    
                        }                                                       
     MAX-ACCESS read-only                                                       
     STATUS current                                                             
     DESCRIPTION                                                                
          "Multicast Send VCC Type. Signalling parameter that                   
           SHOULD be used by the LE Client when establishing                    
           the Multicast Send VCC. This is the method to be used                
           by the LE Client when specifying traffic parameters                  
           when it sets up the Multicast Send VCC for this                      
           emulated LAN. Corresponds to Initial State                           
           Parameter C24."                                                      
     ::= { ibmMvsAtmLecConfigEntry 17 }                                         
                                                                                
     ibmMvsAtmLecMulticastSendAvgRate  OBJECT-TYPE                              
     SYNTAX   Integer32                                                         
     MAX-ACCESS read-only                                                       
     STATUS current                                                             
     DESCRIPTION                                                                
          "Multicast Send VCC AvgRate. Signalling parameter                     
           that SHOULD be used by the LE Client when estabishing                
           the Multicast Send VCC. Forward and Backward Sustained               
           Cell Rate to be requested by LE Client when setting                  
           up Multicast Send VCC, if using Variable bit rate                    
           codings. Corresponds to Initial State Parameter C25."                
     ::= { ibmMvsAtmLecConfigEntry 18 }                                         
                                                                                
     ibmMvsAtmLecMulticastSendPeakRate  OBJECT-TYPE                             
     SYNTAX   Integer32                                                         
     MAX-ACCESS read-only                                                       
     STATUS current                                                             
     DESCRIPTION                                                                
          "Multicast Send VCC PeakRate. Signalling parameter that               
           SHOULD be used by the LE Client when establishing the                
           Multicast Send VCC. Forward and Backward Peak Cell                   
           Rate to be requested by LE Client when setting up the                
           Multicast Send VCC when using either Variable or                     
           Constant bit rate codings. Corresponds to Initial                    
           State Parameter C26."                                                
     ::= { ibmMvsAtmLecConfigEntry 19 }                                         
                                                                                
     ibmMvsAtmLecConnectionCompleteTimer OBJECT-TYPE                            
     SYNTAX   Integer32 (1..10)                                                 
     MAX-ACCESS read-only                                                       
     STATUS current                                                             
     DESCRIPTION                                                                
          "Connection Complete Timer. Optional. In Connection                   
           Establish ment this is the time period in which                      
           data or a READY_IND message is expected from a Calling               
           Party. This time value is expressed in seconds.                      
           Corresponds to Initial State Parameter C28."                         
     ::= { ibmMvsAtmLecConfigEntry 20 }                                         
                                                                                
                                                                                
     ibmMvsAtmLecStatusTable OBJECT-TYPE                                        
     SYNTAX SEQUENCE OF IbmMvsAtmLecStatusEntry                                 
     MAX-ACCESS not-accessible                                                  
     STATUS current                                                             
     DESCRIPTION                                                                
        "This table is intended to represent the data that is                   
         available from an OSA Port that is running SNA LAN                     
         Emulation mode. An entry in this table is indexed a SNA                
         LAN Emulation ifIndex. Am ifEntry who's ifType is either               
         aflane802.3 (59) or aflane802.5 (60) will have a                       
         corresponding entry in this table. This table is modeled               
         after the LEC Status Table from the LAN Emulation MIB                  
         defined by the ATM Forum."                                             
     ::= { ibmTcpipMvsAtmGroup 6 }                                              
                                                                                
     ibmMvsAtmLecStatusEntry OBJECT-TYPE                                        
     SYNTAX IbmMvsAtmLecStatusEntry                                             
     MAX-ACCESS not-accessible                                                  
     STATUS current                                                             
     DESCRIPTION                                                                
        "Describes a particilar ATM Lec Status Table entry, indexed     dex by  
         by either a aflan802.3 or a aflane802.5 ifEntry's ifIndex."            
     INDEX { ifIndex }                                                          
     ::= { ibmMvsAtmLecStatusTable 1 }                                          
                                                                                
     IbmMvsAtmLecStatusEntry ::=                                                
     SEQUENCE                                                                   
       {                                                                        
         ibmMvsAtmLecPrimaryAtmAddress        OCTET STRING(SIZE(20)),           
         ibmMvsAtmLecID                       Integer32,                        
         ibmMvsAtmLecInterfaceState           INTEGER,                          
         ibmMvsAtmLecLastFailureRespCode      INTEGER,                          
         ibmMvsAtmLecLastFailureState         INTEGER,                          
         ibmMvsAtmLecProtocol                 Integer32,                        
         ibmMvsAtmLecVersion                  Integer32,                        
         ibmMvsAtmLecTopologyChange           INTEGER,                          
         ibmMvsAtmLecConfigServerAtmAddress   OCTET STRING(SIZE(20)),           
         ibmMvsAtmLecConfigSource             INTEGER,                          
         ibmMvsAtmLecActualLanType            INTEGER,                          
         ibmMvsAtmLecActualMaxDataFrameSize   INTEGER,                          
         ibmMvsAtmLecActualLanName            OCTET STRING(SIZE(32)),           
         ibmMvsAtmLecAtmAddress               OCTET STRING(SIZE(20)),           
         ibmMvsAtmLecProxyClient              INTEGER                           
       }                                                                        
                                                                                
     ibmMvsAtmLecPrimaryAtmAddress  OBJECT-TYPE                                 
     SYNTAX  OCTET STRING (SIZE(20))                                            
     MAX-ACCESS read-only                                                       
     STATUS current                                                             
     DESCRIPTION                                                                
          "LE Client's ATM Addresses. The primary ATM address                   
           of this LAN Emulation Client. This address is used                   
           to establish the Control Direct and Multicast Send                   
           VCCs, and may also be used to set up Data Direct                     
           VCCs. A client may have additional ATM addresses                     
           for use with Data Direct VCCs. These addresses are                   
           readable via the lecAtmAddressTable. Corresponds to                  
           Initial State Parameter C1."                                         
     ::= { ibmMvsAtmLecStatusEntry 1 }                                          
                                                                                
     ibmMvsAtmLecID  OBJECT-TYPE                                                
     SYNTAX  Integer32 (0..65279)                                               
     MAX-ACCESS read-only                                                       
     STATUS current                                                             
     DESCRIPTION                                                                
          "LE Client Identifier. Each LE Client requires a                      
           LE Client Identifier (LECID) assigned by the LE                      
           Server during the Join phase. The LECID is placed                    
           in control requests by the LE Client and MAY be used                 
           for echo suppression on multicast data frames sent                   
           by that LE Client. This value MUST NOT change without                
           terminating the LE Client and returning to the Initial               
           state. A valid LECID MUST be in the range X'0001'                    
           through X'FEFF'. The value of this object is only                    
           meaningful for a LEC that is connected to a LES. For                 
           a LEC which does not belong to an emulated LAN, the                  
           value of this object is defined to be 0. Corresponds to              
           Initial State Parameter C14."                                        
     ::= { ibmMvsAtmLecStatusEntry 2 }                                          
                                                                                
     ibmMvsAtmLecInterfaceState  OBJECT-TYPE                                    
     SYNTAX  INTEGER {                                                          
                         initialState (1),                                      
                         lecsConnect (2),                                       
                         configure (3),                                         
                         join (4),                                              
                         initialRegistration (5),                               
                         busConnect (6),                                        
                         operational (7)                                        
                       }                                                        
     MAX-ACCESS read-only                                                       
     STATUS current                                                             
     DESCRIPTION                                                                
          "The current state of the LAN Emulation Client. Note                  
           that 'ifOperStatus' is defined to be 'up' when, and                  
           only when, lecInterfaceState' is 'operational'."                     
     ::= { ibmMvsAtmLecStatusEntry 3 }                                          
                                                                                
     ibmMvsAtmLecLastFailureRespCode  OBJECT-TYPE                               
     SYNTAX  INTEGER {                                                          
                         none (1),                                              
                         timeout (2),                                           
                         undefinedError (3),                                    
                         versionNotSupported (4),                               
                         invalidRequestParameters (5),                          
                         duplicateLanDestination (6),                           
                         duplicateAtmAddress (7),                               
                         insufficientResources (8),                             
                         accessDenied (9),                                      
                         invalidRequesterId (10),                               
                         invalidLanDestination (11),                            
                         invalidAtmAddress (12),                                
                         noConfiguration (13),                                  
                         leConfigureError (14),                                 
                         insufficientInformation (15)                           
                       }                                                        
     MAX-ACCESS read-only                                                       
     STATUS current                                                             
     DESCRIPTION                                                                
          "Status code from the last failed Configure response                  
           or Join response. Failed responses are those for which               
           the LE_CONFIGURE_RESPONSE / LE_JOIN_RESPONSE frame                   
           contains a non-zero code, or fails to arrive within a                
           timeout period. If none of this client's requests have               
           failed, this object has the value 'none'. If the                     
           failed response contained a STATUS code that is not                  
           defined in the LAN Emulation specification, this                     
           object has the value 'undefinedError'. The value                     
           'timeout' is self explanatory. Other failure codes                   
           correspond to those defined in the specification,                    
           although they may have different numeric values."                    
     ::= { ibmMvsAtmLecStatusEntry 4 }                                          
                                                                                
     ibmMvsAtmLecLastFailureState  OBJECT-TYPE                                  
     SYNTAX  INTEGER {                                                          
                          initialState (1),                                     
                          lecsConnect (2),                                      
                          configure (3),                                        
                          join (4),                                             
                          initialRegistration (5),                              
                          busConnect (6),                                       
                          operational (7)                                       
                       }                                                        
     MAX-ACCESS read-only                                                       
     STATUS current                                                             
     DESCRIPTION                                                                
          "The state this client was in when it updated the                     
           'lecLastFailureRespCode'. If 'lecLastFailureRespCode'                
           is 'none', this object has the value initialState(1)."               
      ::= { ibmMvsAtmLecStatusEntry 5 }                                         
                                                                                
     ibmMvsAtmLecProtocol  OBJECT-TYPE                                          
     SYNTAX  Integer32 (1..255)                                                 
     MAX-ACCESS read-only                                                       
     STATUS current                                                             
     DESCRIPTION                                                                
          "The LAN Emulation protocol which this client supports,               
           and specifies in its LE_JOIN_REQUESTs."                              
     ::= { ibmMvsAtmLecStatusEntry 6 }                                          
                                                                                
     ibmMvsAtmLecVersion  OBJECT-TYPE                                           
     SYNTAX  Integer32 (1..255)                                                 
     MAX-ACCESS read-only                                                       
     STATUS current                                                             
     DESCRIPTION                                                                
          "The LAN Emulation protocol version which this client                 
           supports, and specifies in its LE_JOIN_REQUESTs."                    
     ::= { ibmMvsAtmLecStatusEntry 7 }                                          
                                                                                
     ibmMvsAtmLecTopologyChange  OBJECT-TYPE                                    
     SYNTAX  INTEGER {                                                          
                         true (1),                                              
                         false (2)                                              
                       }                                                        
     MAX-ACCESS read-only                                                       
     STATUS current                                                             
     DESCRIPTION                                                                
          "Topology Change. Boolean indication that the LE Client               
           is using the Forward Delay Time C18, instead of the                  
           Aging Time C17, to age non-local entries in its LE_ARP               
           cache C16. For a client which is not connected to the                
           LES, this object is defined to have the value 'false'.               
           Corresponds to Initial State Parameter C19."                         
     ::= { ibmMvsAtmLecStatusEntry 8 }                                          
                                                                                
     ibmMvsAtmLecConfigServerAtmAddress  OBJECT-TYPE                            
     SYNTAX  OCTET STRING (SIZE(20))                                            
     MAX-ACCESS read-only                                                       
     STATUS current                                                             
     DESCRIPTION                                                                
          "The ATM address of the LAN Emulation Configuration                   
           Server (if known) or the 0 (otherwise). In LAN                       
           Emulation MIB, the OCTET STRING is either 0 length                   
           or 20 octets. For OSA-ATM, this Address) has been                    
           changed to a constant 20 octets, with the value 0                    
           equivalent to the 0 length OCTET STRING."                            
     ::= { ibmMvsAtmLecStatusEntry 9 }                                          
                                                                                
     ibmMvsAtmLecConfigSource   OBJECT-TYPE                                     
     SYNTAX  INTEGER {                                                          
                         gotAddressViaIlmi(1),                                  
                         usedWellKnownAddress(2),                               
                         usedLecsPvc(3),                                        
                         didNotUseLecs(4)                                       
                       }                                                        
     MAX-ACCESS read-only                                                       
     STATUS current                                                             
     DESCRIPTION                                                                
           "Indicates whether this LAN Emulation Client used the                
            LAN Emulation Configuration Server, and, if so, what                
            method it used to establish the Configuration Direct                
            VCC."                                                               
     ::= { ibmMvsAtmLecStatusEntry 10 }                                         
                                                                                
     ibmMvsAtmLecActualLanType  OBJECT-TYPE                                     
     SYNTAX  INTEGER {                                                          
                         unspecified (1),                                       
                         ethernet (2),                                          
                         tokenRing (3)                                          
                       }                                                        
     MAX-ACCESS read-only                                                       
     STATUS current                                                             
     DESCRIPTION                                                                
           "The data frame format that this LAN Emulation Client                
            is using right now. This may come from lecConfigLanType,            
            the LAN Emulation Configuration Server, or the LAN                  
            Emulation Server. This value is related to 'ifMtu' and              
            'ifType'. See the LEC management specification for more             
            details. Corresponds to Initial State Parameter C2."                
     ::= { ibmMvsAtmLecStatusEntry 11 }                                         
                                                                                
     ibmMvsAtmLecActualMaxDataFrameSize  OBJECT-TYPE                            
     SYNTAX  INTEGER {                                                          
                         unspecified (1),                                       
                         f1516 (2),                                             
                         f4544 (3),                                             
                         f9234 (4),                                             
                         f18190 (5)                                             
                       }                                                        
     MAX-ACCESS read-only                                                       
     STATUS current                                                             
     DESCRIPTION                                                                
           "Maximum Data Frame Size. The maximum data frame size                
            that this LAN Emulation client is using right now.                  
            This may come from lecConfigMaxDataFrameSize,                       
            the LAN Emulation Configuration Server, or the LAN                  
            Emulation Server Corresponds to Initial State                       
            Parameter C3."                                                      
     ::= { ibmMvsAtmLecStatusEntry 12 }                                         
                                                                                
     ibmMvsAtmLecActualLanName  OBJECT-TYPE                                     
     SYNTAX  OCTET STRING (SIZE(32))                                            
     MAX-ACCESS read-only                                                       
     STATUS current                                                             
     DESCRIPTION                                                                
           "ELAN Name. The identity of the emulated LAN which                   
            this client last joined, or wishes to join. This                    
            may come from lecConfigLanName, the LAN Emulation                   
            Configuration Server, or the LAN Emulation Server.                  
            Corresponds to Initial State Parameter C5."                         
     ::= { ibmMvsAtmLecStatusEntry 13 }                                         
                                                                                
     ibmMvsAtmLecAtmAddress  OBJECT-TYPE                                        
     SYNTAX  OCTET STRING (SIZE(20))                                            
     MAX-ACCESS read-only                                                       
     STATUS current                                                             
     DESCRIPTION                                                                
           "LE Server ATM Address. The LAN Emulation Server                     
            address currently in use or most recently attempted.                
            If no LAN Emulation Server attachment has been tried,               
            this object's value is zero. Corresponds to Initial                 
            State Parameter C9. In LAN Emulation MIB, the                       
            OCTET STRING is 0 to 20 octets in length. For OSA-ATM,              
            this has been changed to a constant 20 octets, with                 
            the value 0 equivalent to the 0 length OCTET STRING."               
     ::= { ibmMvsAtmLecStatusEntry 14 }                                         
                                                                                
     ibmMvsAtmLecProxyClient  OBJECT-TYPE                                       
     SYNTAX  INTEGER {                                                          
                         true (1),                                              
                         false (2)                                              
                       }                                                        
     MAX-ACCESS read-only                                                       
     STATUS current                                                             
     DESCRIPTION                                                                
           "Indicates whether this client is acting as a proxy.                 
            Proxy clients are allowed to represent unregistered                 
            MAC addresses, and receive copies of LE_ARP_REQUEST                 
            frames for such addresses. Corresponds to Initial                   
            State Parameter C4."                                                
     ::= { ibmMvsAtmLecStatusEntry 15 }                                         
                                                                                
     ibmMvsAtmLecStatisticsTable OBJECT-TYPE                                    
     SYNTAX SEQUENCE OF IbmMvsAtmLecStatisticsEntry                             
     MAX-ACCESS not-accessible                                                  
     STATUS current                                                             
     DESCRIPTION                                                                
        "This table is intended to represent the data that is                   
         available from an OSA Port that is running SNA LAN                     
         Emulation mode. An entry in this table is indexed a SNA                
         LAN Emulation ifIndex. Am ifEntry who's ifType is either               
         aflane802.3 (59) or aflane802.5 (60) will have a                       
         corresponding entry in this table. This table is modeled               
         after the LEC Statistics Table from the LAN Emulation MIB              
         defined by the ATM Forum."                                             
     ::= { ibmTcpipMvsAtmGroup 7 }                                              
                                                                                
     ibmMvsAtmLecStatisticsEntry OBJECT-TYPE                                    
     SYNTAX IbmMvsAtmLecStatisticsEntry                                         
     MAX-ACCESS not-accessible                                                  
     STATUS current                                                             
     DESCRIPTION                                                                
        "Describes a particilar ATM Lec Statistics Table entry, indexed dex by  
         by either a aflan802.3 or a aflane802.5 ifEntry's ifIndex."            
     INDEX { ifIndex }                                                          
     ::= { ibmMvsAtmLecStatisticsTable 1 }                                      
                                                                                
     IbmMvsAtmLecStatisticsEntry ::=                                            
     SEQUENCE                                                                   
       {                                                                        
         ibmMvsAtmLecArpRequestsOut      Counter32,                             
         ibmMvsAtmLecArpRequestsIn       Counter32,                             
         ibmMvsAtmLecArpRepliesOut       Counter32,                             
         ibmMvsAtmLecArpRepliesIn        Counter32,                             
         ibmMvsAtmLecControlFramesOut    Counter32,                             
         ibmMvsAtmLecControlFramesIn     Counter32,                             
         ibmMvsAtmLecSvcFailures         Counter32                              
       }                                                                        
                                                                                
     ibmMvsAtmLecArpRequestsOut  OBJECT-TYPE                                    
     SYNTAX  Counter32                                                          
     MAX-ACCESS read-only                                                       
     STATUS current                                                             
     DESCRIPTION                                                                
           "The number of LE_ARP_REQUESTs sent over the                         
            LUNI by this LAN Emulation Client."                                 
     ::= { ibmMvsAtmLecStatisticsEntry 1 }                                      
                                                                                
     ibmMvsAtmLecArpRequestsIn OBJECT-TYPE                                      
     SYNTAX  Counter32                                                          
     MAX-ACCESS read-only                                                       
     STATUS current                                                             
     DESCRIPTION                                                                
           "The number of LE_ARP_REQUESTs received over the LUNI                
            by this LAN Emulation Client. Requests may arrive                   
            on the Control Direct VCC or on the Control Distribute              
            VCC, depending upon how the LES is implemented and the              
            chances it has had for learning. This counter covers                
            both VCCs."                                                         
     ::= { ibmMvsAtmLecStatisticsEntry 2 }                                      
                                                                                
     ibmMvsAtmLecArpRepliesOut  OBJECT-TYPE                                     
     SYNTAX  Counter32                                                          
     MAX-ACCESS read-only                                                       
     STATUS current                                                             
     DESCRIPTION                                                                
           "The number of LE_ARP_RESPONSEs sent over the LUNI                   
            by this LAN Emulation Client."                                      
     ::= { ibmMvsAtmLecStatisticsEntry 3 }                                      
                                                                                
     ibmMvsAtmLecArpRepliesIn  OBJECT-TYPE                                      
     SYNTAX  Counter32                                                          
     MAX-ACCESS read-only                                                       
     STATUS current                                                             
     DESCRIPTION                                                                
           "The number of LE_ARP_RESPONSEs received over the                    
            LUNI by this LAN Emulation Client. This count includes              
            all such replies, whether solicited or not. Replies                 
            may arrive on the Control Direct VCC or on the                      
            Control Distribute VCC, depending upon how the LES                  
            is implemented. This counter covers both VCCs."                     
     ::= { ibmMvsAtmLecStatisticsEntry 4 }                                      
                                                                                
     ibmMvsAtmLecControlFramesOut OBJECT-TYPE                                   
     SYNTAX  Counter32                                                          
     MAX-ACCESS read-only                                                       
     STATUS current                                                             
     DESCRIPTION                                                                
           "The total number of control packets sent by this                    
            LAN Emulation Client over the LUNI."                                
     ::= { ibmMvsAtmLecStatisticsEntry 5 }                                      
                                                                                
     ibmMvsAtmLecControlFramesIn OBJECT-TYPE                                    
     SYNTAX  Counter32                                                          
     MAX-ACCESS read-only                                                       
     STATUS current                                                             
     DESCRIPTION                                                                
           "The total number of control packets received by this                
           LAN Emulation Client over the LUNI."                                 
     ::= { ibmMvsAtmLecStatisticsEntry 6 }                                      
                                                                                
     ibmMvsAtmLecSvcFailures OBJECT-TYPE                                        
     SYNTAX  Counter32                                                          
     MAX-ACCESS read-only                                                       
     STATUS current                                                             
     DESCRIPTION                                                                
           "The total number of outgoing LAN Emulation SVCs                     
            which this client tried, but failed, to open;                       
            incoming LAN Emulation SVCs which this client tried,                
            but failed to establish; and incoming LAN Emulation                 
            SVCs which this client rejected for protocol or                     
            security reasons."                                                  
     ::= { ibmMvsAtmLecStatisticsEntry 7 }                                      
                                                                                
                                                                                
     ibmMvsAtmLecServerTable OBJECT-TYPE                                        
     SYNTAX SEQUENCE OF IbmMvsAtmLecServerEntry                                 
     MAX-ACCESS not-accessible                                                  
     STATUS current                                                             
     DESCRIPTION                                                                
        "This table is intended to represent the data that is                   
         available from an OSA Port that is running SNA LAN                     
         Emulation mode. An entry in this table is indexed a SNA                
         LAN Emulation ifIndex. Am ifEntry who's ifType is either               
         aflane802.3 (59) or aflane802.5 (60) will have a                       
         corresponding entry in this table. This table is modeled               
         after the LEC Server Table from the LAN Emulation MIB                  
         defined by the ATM Forum."                                             
     ::= { ibmTcpipMvsAtmGroup 8 }                                              
                                                                                
     ibmMvsAtmLecServerEntry OBJECT-TYPE                                        
     SYNTAX IbmMvsAtmLecServerEntry                                             
     MAX-ACCESS not-accessible                                                  
     STATUS current                                                             
     DESCRIPTION                                                                
        "Describes a particilar ATM Lec Server Table entry, indexed     dex by  
         by either a aflan802.3 or a aflane802.5 ifEntry's ifIndex."            
     INDEX { ifIndex }                                                          
     ::= { ibmMvsAtmLecServerTable 1 }                                          
                                                                                
     IbmMvsAtmLecServerEntry ::=                                                
     SEQUENCE                                                                   
       {                                                                        
        ibmMvsAtmLecConfigDirectInterface       Integer32,                      
        ibmMvsAtmLecConfigDirectVPI             Integer32,                      
        ibmMvsAtmLecConfigDirectVCI             Integer32,                      
        ibmMvsAtmLecControlDirectInterface      Integer32,                      
        ibmMvsAtmLecControlDirectVPI            Integer32,                      
        ibmMvsAtmLecControlDirectVCI            Integer32,                      
        ibmMvsAtmLecControlDistributeInterface  Integer32,                      
        ibmMvsAtmLecControlDistributeVPI        Integer32,                      
        ibmMvsAtmLecControlDistributeVCI        Integer32,                      
        ibmMvsAtmLecMulticastSendInterface      Integer32,                      
        ibmMvsAtmLecMulticastSendVPI            Integer32,                      
        ibmMvsAtmLecMulticastSendVCI            Integer32,                      
        ibmMvsAtmLecMulticastFwdInterface       Integer32,                      
        ibmMvsAtmLecMulticastFwdVPI             Integer32,                      
        ibmMvsAtmLecMulticastFwdVCI             Integer32                       
       }                                                                        
                                                                                
     ibmMvsAtmLecConfigDirectInterface  OBJECT-TYPE                             
     SYNTAX  Integer32 (0..2147483647)                                          
     MAX-ACCESS read-only                                                       
     STATUS current                                                             
     DESCRIPTION                                                                
             "The interface associated with the Configuration                   
              Direct VCC. If no Configuration Direct VCC exists,                
              this object has the value 0. Otherwise, the objects               
              ( lecConfigDirectInterface, lecConfigDirectVPI,                   
              lecConfigDirectVCI ) identify the circuit."                       
     ::= { ibmMvsAtmLecServerEntry 1 }                                          
                                                                                
     ibmMvsAtmLecConfigDirectVPI  OBJECT-TYPE                                   
     SYNTAX  Integer32 (0..255)                                                 
     MAX-ACCESS read-only                                                       
     STATUS current                                                             
     DESCRIPTION                                                                
             "If the Configuration Direct VCC exists, this object               
              contains the VPI which identifies that VCC at the                 
              point where it connects to this LE client.                        
              Otherwise, this object has the value 0."                          
     ::= { ibmMvsAtmLecServerEntry 2 }                                          
                                                                                
     ibmMvsAtmLecConfigDirectVCI  OBJECT-TYPE                                   
     SYNTAX  Integer32 (0..65535)                                               
     MAX-ACCESS read-only                                                       
     STATUS current                                                             
     DESCRIPTION                                                                
             "If the Configuration Direct VCC exists, this                      
              object contains the VCI which identifies that                     
              VCC at the point where it connects to this LE                     
              client. Otherwise, this object has the value 0."                  
     ::= { ibmMvsAtmLecServerEntry 3 }                                          
                                                                                
     ibmMvsAtmLecControlDirectInterface  OBJECT-TYPE                            
     SYNTAX  Integer32 (0..2147483647)                                          
     MAX-ACCESS read-only                                                       
     STATUS current                                                             
     DESCRIPTION                                                                
           "The interface associated with the Control Direct                    
            VCC. If no Control Direct VCC exists, this object                   
            has the value 0. Otherwise, the objects                             
            ( lecControlDirectInterface, lecControlDirectVPI,                   
            lecControlDirectVCI ) identify the circuit."                        
     ::= { ibmMvsAtmLecServerEntry 4 }                                          
                                                                                
     ibmMvsAtmLecControlDirectVPI OBJECT-TYPE                                   
     SYNTAX  Integer32 (0..255)                                                 
     MAX-ACCESS read-only                                                       
     STATUS current                                                             
     DESCRIPTION                                                                
           "If the Control Direct VCC exists, this object                       
            contains the VPI which identifies that VCC at                       
            the point where it connects to this LE client.                      
            Otherwise, this object has the value 0."                            
     ::= { ibmMvsAtmLecServerEntry 5 }                                          
                                                                                
     ibmMvsAtmLecControlDirectVCI OBJECT-TYPE                                   
     SYNTAX  Integer32 (0..65535)                                               
     MAX-ACCESS read-only                                                       
     STATUS current                                                             
     DESCRIPTION                                                                
           "If the Control Direct VCC exists, this object                       
            contains the VCI which identifies that VCC at                       
            the point where it connects to this LE client.                      
            Otherwise, this object has the value 0."                            
     ::= { ibmMvsAtmLecServerEntry 6 }                                          
                                                                                
     ibmMvsAtmLecControlDistributeInterface OBJECT-TYPE                         
     SYNTAX  Integer32 (0..2147483647)                                          
     MAX-ACCESS read-only                                                       
     STATUS current                                                             
     DESCRIPTION                                                                
           "The interface associated with the Control Distribute                
            VCC. If no Control Distribute VCC has been set up to                
            this client, this object has the value 0. Otherwise,                
            the objects ( lecControlDistributeInterface,                        
            lecControlDistributeVPI, lecControlDistributeVCI )                  
            identify the circuit."                                              
     ::= { ibmMvsAtmLecServerEntry 7 }                                          
                                                                                
     ibmMvsAtmLecControlDistributeVPI  OBJECT-TYPE                              
     SYNTAX  Integer32 (0..255)                                                 
     MAX-ACCESS read-only                                                       
     STATUS current                                                             
     DESCRIPTION                                                                
           "If the Control Distribute VCC exists, this object                   
            contains the VPI which identifies that VCC at the                   
            point where it connects to this LE client.                          
            Otherwise, this object has the value 0."                            
     ::= { ibmMvsAtmLecServerEntry 8 }                                          
                                                                                
     ibmMvsAtmLecControlDistributeVCI  OBJECT-TYPE                              
     SYNTAX  Integer32 (0..65535)                                               
     MAX-ACCESS read-only                                                       
     STATUS current                                                             
     DESCRIPTION                                                                
           "If the Control Distribute VCC exists, this object                   
            contains the VCI which identifies that VCC at the                   
            point where it connects to this LE client.                          
            Otherwise, this object contains the value 0."                       
     ::= { ibmMvsAtmLecServerEntry 9 }                                          
                                                                                
     ibmMvsAtmLecMulticastSendInterface  OBJECT-TYPE                            
     SYNTAX  Integer32 (0..2147483647)                                          
     MAX-ACCESS read-only                                                       
     STATUS current                                                             
     DESCRIPTION                                                                
          "The interface associated with the Multicast Send                     
           VCC. If no Multicast Send VCC exists, this object                    
           has the value 0. Otherwise, the objects                              
           ( lecMulticastSendInterface, lecMulticastSendVPI,                    
           lecMulticastSendVCI ) identify the circuit."                         
     ::= { ibmMvsAtmLecServerEntry 10 }                                         
                                                                                
     ibmMvsAtmLecMulticastSendVPI  OBJECT-TYPE                                  
     SYNTAX  Integer32 (0..255)                                                 
     MAX-ACCESS read-only                                                       
     STATUS current                                                             
     DESCRIPTION                                                                
          "If the Multicast Send VCC exists, this object                        
           contains the VPI which identifies that VCC at                        
           the point where it connects to this LE client.                       
           Otherwise, this object has the value 0."                             
     ::= { ibmMvsAtmLecServerEntry 11 }                                         
                                                                                
     ibmMvsAtmLecMulticastSendVCI  OBJECT-TYPE                                  
     SYNTAX  Integer32 (0..65535)                                               
     MAX-ACCESS read-only                                                       
     STATUS current                                                             
     DESCRIPTION                                                                
          "If the Multicast Send VCC exists, this object                        
           contains the VCI which identifies that VCC at                        
           the point where it connects to this LE client.                       
           Otherwise, this object has the value 0."                             
     ::= { ibmMvsAtmLecServerEntry 12 }                                         
                                                                                
     ibmMvsAtmLecMulticastFwdInterface  OBJECT-TYPE                             
     SYNTAX  Integer32 (0..2147483647)                                          
     MAX-ACCESS read-only                                                       
     STATUS current                                                             
     DESCRIPTION                                                                
           "The interface associated with the Multicast                         
            Forward VCC. If no Multicast Forward VCC has                        
            been set up to this client, this object has the                     
            value 0. Otherwise, the objects                                     
            ( lecMulticastForwardInterface, lecMulticastForwardVPI,             
            lecMulticastForwardVCI ) identify the circuit."                     
     ::= { ibmMvsAtmLecServerEntry 13 }                                         
                                                                                
     ibmMvsAtmLecMulticastFwdVPI  OBJECT-TYPE                                   
     SYNTAX  Integer32 (0..255)                                                 
     MAX-ACCESS read-only                                                       
     STATUS current                                                             
     DESCRIPTION                                                                
           "If the Multicast Forward VCC exists, this object                    
            contains the VPI which identifies that VCC at the                   
            point where it connects to this LE client.                          
            Otherwise, this object has the value 0."                            
     ::= { ibmMvsAtmLecServerEntry 14 }                                         
                                                                                
     ibmMvsAtmLecMulticastFwdVCI  OBJECT-TYPE                                   
     SYNTAX  Integer32 (0..65535)                                               
     MAX-ACCESS read-only                                                       
     STATUS current                                                             
     DESCRIPTION                                                                
           "If the Multicast Forward VCC exists, this object                    
            contains the VCI which identifies that VCC at the                   
            point where it connects to this LE client.                          
            Otherwise, this object has the value 0."                            
     ::= { ibmMvsAtmLecServerEntry 15 }                                         
                                                                                
     ibmMvsAtmLecMacAddressTable OBJECT-TYPE                                    
     SYNTAX SEQUENCE OF IbmMvsAtmLecMacAddressEntry                             
     MAX-ACCESS not-accessible                                                  
     STATUS current                                                             
     DESCRIPTION                                                                
        "This table is intended to represent the data that is                   
         available from an OSA Port that is running SNA LAN                     
         Emulation mode. An entry in this table is indexed a SNA                
         LAN Emulation ifIndex. An ifEntry who's ifType is either               
         aflane802.3 (59) or aflane802.5 (60) will have a                       
         corresponding entry in this table. This table is modeled               
         after the LEC MAC Address Table from the LAN Emulation MIB             
         defined by the ATM Forum."                                             
     ::= { ibmTcpipMvsAtmGroup 9 }                                              
                                                                                
     ibmMvsAtmLecMacAddressEntry OBJECT-TYPE                                    
     SYNTAX IbmMvsAtmLecMacAddressEntry                                         
     MAX-ACCESS not-accessible                                                  
     STATUS current                                                             
     DESCRIPTION                                                                
        "Describes a particilar ATM Lec Mac Address Table entry,                
         indexed by either a aflan802.3 or a aflane802.5 ifEntry's              
         ifIndex."                                                              
     INDEX { ifIndex }                                                          
     ::= { ibmMvsAtmLecMacAddressTable 1 }                                      
                                                                                
     IbmMvsAtmLecMacAddressEntry ::=                                            
     SEQUENCE                                                                   
       {                                                                        
          ibmMvsAtmLecMacAddress    OCTET STRING (SIZE(6))                      
       }                                                                        
                                                                                
     ibmMvsAtmLecMacAddress  OBJECT-TYPE                                        
     SYNTAX  OCTET STRING (SIZE(6))                                             
     MAX-ACCESS read-only                                                       
     STATUS current                                                             
     DESCRIPTION                                                                
         "A unicast MAC address which the LE client                             
          denoted by 'lecIndex' has registered with its                         
          LE Server. This value is expressed in canonical                       
          form for Ethernet."                                                   
     ::= { ibmMvsAtmLecMacAddressEntry 1 }                                      
                                                                                
                                                                                
                                                                                
 ---------------------------------------------------------------------          
 -- ibmTcpipMvsTcpGroup                                                         
 ---------------------------------------------------------------------          
                                                                                
     ibmTcpipMvsTcpConnTable OBJECT-TYPE                                        
     SYNTAX SEQUENCE OF IbmTcpipMvsTcpConnEntry                                 
     MAX-ACCESS not-accessible                                                  
     STATUS current                                                             
     DESCRIPTION                                                                
          "Extends tcpConnTable to support gateway semantic."                   
     ::= { ibmTcpipMvsTcpGroup 1 }                                              
                                                                                
     ibmTcpipMvsTcpConnEntry OBJECT-TYPE                                        
     SYNTAX IbmTcpipMvsTcpConnEntry                                             
     MAX-ACCESS not-accessible                                                  
     STATUS current                                                             
     DESCRIPTION                                                                
          "Descibes a particular tcp connection entry."                         
     AUGMENTS { tcpConnEntry }                                                  
     ::= { ibmTcpipMvsTcpConnTable 1 }                                          
                                                                                
     IbmTcpipMvsTcpConnEntry ::=                                                
          SEQUENCE                                                              
          {                                                                     
          ibmMvsTcpConnLastActivity       TimeTicks,                            
          ibmMvsTcpConnBytesIn            Integer32,                            
          ibmMvsTcpConnBytesOut           Integer32,                            
          ibmMvsTcpConnActiveOpen         Integer32,                            
          ibmMvsTcpConnIpTos              TypeOfService,                        
          ibmMvsTcpConnOptions            OCTET STRING  (SIZE(1..40)),          
          ibmMvsTcpConnOutBuffered        Integer32,                            
          ibmMvsTcpConnUsrSndNxt          Integer32,                            
          ibmMvsTcpConnSndNxt             Integer32,                            
          ibmMvsTcpConnSndUna             Integer32,                            
          ibmMvsTcpConnOutgoingPush       Integer32,                            
          ibmMvsTcpConnOutgoingUrg        Integer32,                            
          ibmMvsTcpConnOutgoingWinSeq     Integer32,                            
          ibmMvsTcpConnSendWindowSeq      Integer32,                            
          ibmMvsTcpConnSendWindowAck      Integer32,                            
          ibmMvsTcpConnInBuffered         Integer32,                            
          ibmMvsTcpConnRcvNxt             Integer32,                            
          ibmMvsTcpConnUsrRcvNxt          Integer32,                            
          ibmMvsTcpConnIncomingPush       Integer32,                            
          ibmMvsTcpConnIncomingUrg        Integer32,                            
          ibmMvsTcpConnIncomingWinSeq     Integer32,                            
          ibmMvsTcpConnReXmt              Integer32,                            
          ibmMvsTcpConnMaxSndWnd          Integer32,                            
          ibmMvsTcpConnReXmtCount         Integer32,                            
          ibmMvsTcpConnCongestionWnd      Integer32,                            
          ibmMvsTcpConnSSThresh           Integer32,                            
          ibmMvsTcpConnRoundTripTime      Integer32,                            
          ibmMvsTcpConnRoundTripVariance  Integer32,                            
          ibmMvsTcpConnInitSndSeq         Integer32,                            
          ibmMvsTcpConnInitRcvSeq         Integer32,                            
          ibmMvsTcpConnSendMSS            Integer32,                            
          ibmMvsTcpConnSndWl1             Integer32,                            
          ibmMvsTcpConnSndWl2             Integer32,                            
          ibmMvsTcpConnSndWnd             Integer32,                            
          ibmMvsTcpConnPendTcpRecv        Integer32,                            
          ibmMvsTcpConnRcvBufSize         Integer32,                            
          ibmMvsTcpConnResourceName       DisplayString  (SIZE(0..8)),          
          ibmMvsTcpConnSubtask            Integer32,                            
          ibmMvsTcpConnResourceId         Integer32,                            
          ibmMvsTcpConnSockOpt            OCTET STRING (SIZE(1)),               
          ibmMvsTcpConnTcpTimer           Integer32,                            
          ibmMvsTcpConnTcpSig             Integer32,                            
          ibmMvsTcpConnTcpSel             Integer32,                            
          ibmMvsTcpConnRttSeq             Integer32,                            
          ibmMvsTcpConnBackoffCount       Integer32,                            
          ibmMvsTcpConnTcpDet             OCTET STRING (SIZE(1)),               
          ibmMvsTcpConnTcpPol             OCTET STRING (SIZE(1)),               
          ibmMvsTcpConnTargetAppl         DisplayString  (SIZE(0..8)),          
          ibmMvsTcpConnLuName             DisplayString  (SIZE(0..8)),          
          ibmMvsTcpConnClientUserId       DisplayString  (SIZE(0..8)),          
          ibmMvsTcpConnLogMode            DisplayString  (SIZE(0..8)),          
          ibmMvsTcpConnProto              OCTET STRING (SIZE(1)),               
          ibmMvsTcpConnDupacks            Integer32,                            
          ibmMvsTcpConnOptMaxSegmentSize  Integer32                             
          }                                                                     
                                                                                
       ibmMvsTcpConnLastActivity OBJECT-TYPE                                    
             SYNTAX   TimeTicks                                                 
             MAX-ACCESS   read-only                                             
             STATUS   current                                                   
             DESCRIPTION                                                        
                "The number of 100ths of seconds  since  this  entry            
                was last used."                                                 
             DEFVAL  { 0 }                                                      
             ::= { ibmTcpipMvsTcpConnEntry 1 }                                  
                                                                                
          ibmMvsTcpConnBytesIn  OBJECT-TYPE                                     
             SYNTAX   Integer32                                                 
             MAX-ACCESS   read-only                                             
             STATUS   current                                                   
             DESCRIPTION                                                        
                "The number of bytes received from IP for this                  
                 connection."                                                   
             DEFVAL  { 0 }                                                      
             ::= { ibmTcpipMvsTcpConnEntry 2 }                                  
                                                                                
          ibmMvsTcpConnBytesOut OBJECT-TYPE                                     
             SYNTAX   Integer32                                                 
             MAX-ACCESS   read-only                                             
             STATUS   current                                                   
             DESCRIPTION                                                        
                "The number of bytes sent to IP for this connection."           
             DEFVAL  { 0 }                                                      
             ::= { ibmTcpipMvsTcpConnEntry 3 }                                  
                                                                                
          ibmMvsTcpConnActiveOpen OBJECT-TYPE                                   
             SYNTAX   Integer32                                                 
             MAX-ACCESS   read-only                                             
             STATUS   current                                                   
             DESCRIPTION                                                        
                "The number of times that this connection has made a            
                 direct transition to the SYN-RCVD state from the               
                 listen state."                                                 
             DEFVAL  { 0 }                                                      
             ::= { ibmTcpipMvsTcpConnEntry 4 }                                  
                                                                                
          ibmMvsTcpConnIpTos OBJECT-TYPE                                        
             SYNTAX   TypeOfService                                             
             MAX-ACCESS   read-only                                             
             STATUS   current                                                   
             DESCRIPTION                                                        
                "Type of Service (tos) in effect for this tcpConnTable          
                 entry. Currently not supported and should return a             
                 zero."                                                         
             ::= { ibmTcpipMvsTcpConnEntry 5 }                                  
                                                                                
          ibmMvsTcpConnOptions OBJECT-TYPE                                      
             SYNTAX   OCTET STRING (SIZE(1..40))                                
             MAX-ACCESS   read-only                                             
             STATUS   current                                                   
             DESCRIPTION                                                        
                "IP options (see RFC 791)"                                      
             ::= { ibmTcpipMvsTcpConnEntry 6 }                                  
                                                                                
          ibmMvsTcpConnOutBuffered OBJECT-TYPE                                  
             SYNTAX   Integer32                                                 
             MAX-ACCESS   read-only                                             
             STATUS   current                                                   
             DESCRIPTION                                                        
                "Number of outgoing bytes buffered"                             
             DEFVAL  { 0 }                                                      
             ::= { ibmTcpipMvsTcpConnEntry 7 }                                  
                                                                                
          ibmMvsTcpConnUsrSndNxt OBJECT-TYPE                                    
             SYNTAX   Integer32                                                 
             MAX-ACCESS   read-only                                             
             STATUS   current                                                   
             DESCRIPTION                                                        
                "Sequence number of next byte for user"                         
             DEFVAL  { 0 }                                                      
             ::= { ibmTcpipMvsTcpConnEntry 8 }                                  
                                                                                
          ibmMvsTcpConnSndNxt OBJECT-TYPE                                       
             SYNTAX   Integer32                                                 
             MAX-ACCESS   read-only                                             
             STATUS   current                                                   
             DESCRIPTION                                                        
                "Sequence number of next byte for TCP"                          
             DEFVAL  { 0 }                                                      
             ::= { ibmTcpipMvsTcpConnEntry 9 }                                  
                                                                                
          ibmMvsTcpConnSndUna OBJECT-TYPE                                       
             SYNTAX   Integer32                                                 
             MAX-ACCESS   read-only                                             
             STATUS   current                                                   
             DESCRIPTION                                                        
                "Sequence number of sent/unacked byte"                          
             DEFVAL  { 0 }                                                      
             ::= { ibmTcpipMvsTcpConnEntry 10 }                                 
                                                                                
          ibmMvsTcpConnOutgoingPush OBJECT-TYPE                                 
             SYNTAX   Integer32                                                 
             MAX-ACCESS   read-only                                             
             STATUS   current                                                   
             DESCRIPTION                                                        
                "Sequence number of last pushed byte"                           
             DEFVAL  { 0 }                                                      
             ::= { ibmTcpipMvsTcpConnEntry 11 }                                 
                                                                                
          ibmMvsTcpConnOutgoingUrg OBJECT-TYPE                                  
             SYNTAX   Integer32                                                 
             MAX-ACCESS   read-only                                             
             STATUS   current                                                   
             DESCRIPTION                                                        
                "Sequence number of last urg byte"                              
             DEFVAL  { 0 }                                                      
             ::= { ibmTcpipMvsTcpConnEntry 12 }                                 
                                                                                
          ibmMvsTcpConnOutgoingWinSeq OBJECT-TYPE                               
             SYNTAX   Integer32                                                 
             MAX-ACCESS   read-only                                             
             STATUS   current                                                   
             DESCRIPTION                                                        
                "Last sequence number in snd window"                            
             DEFVAL  { 0 }                                                      
             ::= { ibmTcpipMvsTcpConnEntry 13 }                                 
                                                                                
          ibmMvsTcpConnSendWindowSeq OBJECT-TYPE                                
             SYNTAX   Integer32                                                 
             MAX-ACCESS   read-only                                             
             STATUS   obsolete                                                  
             DESCRIPTION                                                        
                "Last sequence number used, win update"                         
             DEFVAL  { 0 }                                                      
             ::= { ibmTcpipMvsTcpConnEntry 14 }                                 
                                                                                
          ibmMvsTcpConnSendWindowAck OBJECT-TYPE                                
             SYNTAX   Integer32                                                 
             MAX-ACCESS   read-only                                             
             STATUS   obsolete                                                  
             DESCRIPTION                                                        
                "Last Ack number used, win update"                              
             DEFVAL  { 0 }                                                      
             ::= { ibmTcpipMvsTcpConnEntry 15 }                                 
                                                                                
          ibmMvsTcpConnInBuffered OBJECT-TYPE                                   
             SYNTAX   Integer32                                                 
             MAX-ACCESS   read-only                                             
             STATUS current                                                     
             DESCRIPTION                                                        
                "Number of incoming bytes buffered"                             
             DEFVAL  { 0 }                                                      
             ::= { ibmTcpipMvsTcpConnEntry 16 }                                 
                                                                                
          ibmMvsTcpConnRcvNxt OBJECT-TYPE                                       
             SYNTAX   Integer32                                                 
             MAX-ACCESS   read-only                                             
             STATUS   current                                                   
             DESCRIPTION                                                        
                "Sequence number of next byte for TCP"                          
             DEFVAL  { 0 }                                                      
             ::= { ibmTcpipMvsTcpConnEntry 17 }                                 
                                                                                
          ibmMvsTcpConnUsrRcvNxt OBJECT-TYPE                                    
             SYNTAX   Integer32                                                 
             MAX-ACCESS   read-only                                             
             STATUS   current                                                   
             DESCRIPTION                                                        
                "Sequence number of next byte for user"                         
             DEFVAL  { 0 }                                                      
             ::= { ibmTcpipMvsTcpConnEntry 18 }                                 
                                                                                
          ibmMvsTcpConnIncomingPush OBJECT-TYPE                                 
             SYNTAX   Integer32                                                 
             MAX-ACCESS   read-only                                             
             STATUS   current                                                   
             DESCRIPTION                                                        
                "Sequence number of last pushed byte"                           
             DEFVAL  { 0 }                                                      
             ::= { ibmTcpipMvsTcpConnEntry 19 }                                 
                                                                                
          ibmMvsTcpConnIncomingUrg OBJECT-TYPE                                  
             SYNTAX   Integer32                                                 
             MAX-ACCESS   read-only                                             
             STATUS   current                                                   
             DESCRIPTION                                                        
                "Sequence number of 'urgent' byte received"                     
             DEFVAL  { 0 }                                                      
             ::= { ibmTcpipMvsTcpConnEntry 20 }                                 
                                                                                
          ibmMvsTcpConnIncomingWinSeq OBJECT-TYPE                               
             SYNTAX   Integer32                                                 
             MAX-ACCESS   read-only                                             
             STATUS   current                                                   
             DESCRIPTION                                                        
                "Last sequence number in receive window"                        
             DEFVAL  { 0 }                                                      
             ::= { ibmTcpipMvsTcpConnEntry 21 }                                 
                                                                                
          ibmMvsTcpConnReXmt OBJECT-TYPE                                        
             SYNTAX   Integer32                                                 
             MAX-ACCESS   read-only                                             
             STATUS   current                                                   
             DESCRIPTION                                                        
                "Number of retransmissions"                                     
             DEFVAL  { 0 }                                                      
             ::= { ibmTcpipMvsTcpConnEntry 22 }                                 
                                                                                
          ibmMvsTcpConnMaxSndWnd OBJECT-TYPE                                    
             SYNTAX   Integer32                                                 
             MAX-ACCESS   read-only                                             
             STATUS   current                                                   
             DESCRIPTION                                                        
                "Maximum send window seen"                                      
             DEFVAL  { 0 }                                                      
             ::= { ibmTcpipMvsTcpConnEntry 23 }                                 
                                                                                
          ibmMvsTcpConnReXmtCount OBJECT-TYPE                                   
             SYNTAX   Integer32                                                 
             MAX-ACCESS   read-only                                             
             STATUS   current                                                   
             DESCRIPTION                                                        
                "Current retransmission count"                                  
             DEFVAL  { 0 }                                                      
             ::= { ibmTcpipMvsTcpConnEntry 24 }                                 
                                                                                
          ibmMvsTcpConnCongestionWnd OBJECT-TYPE                                
             SYNTAX   Integer32                                                 
             MAX-ACCESS   read-only                                             
             STATUS   current                                                   
             DESCRIPTION                                                        
                "Congestion window"                                             
             DEFVAL  { 0 }                                                      
             ::= { ibmTcpipMvsTcpConnEntry 25 }                                 
                                                                                
          ibmMvsTcpConnSSThresh OBJECT-TYPE                                     
             SYNTAX   Integer32                                                 
             MAX-ACCESS   read-only                                             
             STATUS   current                                                   
             DESCRIPTION                                                        
                "Slow start threshold"                                          
             DEFVAL  { 0 }                                                      
             ::= { ibmTcpipMvsTcpConnEntry 26 }                                 
                                                                                
          ibmMvsTcpConnRoundTripTime OBJECT-TYPE                                
             SYNTAX   Integer32                                                 
             MAX-ACCESS   read-only                                             
             STATUS   current                                                   
             DESCRIPTION                                                        
                "The amount of time that has elapsed, measured in               
                 milliseconds, from when the last TCP segment was               
                 transmitted by the TCP Stack until the ACK was                 
                 received."                                                     
             DEFVAL  { 0 }                                                      
             ::= { ibmTcpipMvsTcpConnEntry 27 }                                 
                                                                                
          ibmMvsTcpConnRoundTripVariance OBJECT-TYPE                            
             SYNTAX   Integer32                                                 
             MAX-ACCESS   read-only                                             
             STATUS   current                                                   
             DESCRIPTION                                                        
                "Round trip time variance."                                     
             DEFVAL  { 0 }                                                      
             ::= { ibmTcpipMvsTcpConnEntry 28 }                                 
                                                                                
          ibmMvsTcpConnInitSndSeq OBJECT-TYPE                                   
             SYNTAX   Integer32                                                 
             MAX-ACCESS   read-only                                             
             STATUS   current                                                   
             DESCRIPTION                                                        
                "Initial Send Sequence Number"                                  
             DEFVAL  { 0 }                                                      
             ::= { ibmTcpipMvsTcpConnEntry 29 }                                 
                                                                                
          ibmMvsTcpConnInitRcvSeq OBJECT-TYPE                                   
             SYNTAX   Integer32                                                 
             MAX-ACCESS   read-only                                             
             STATUS   current                                                   
             DESCRIPTION                                                        
                "Initial Receive Sequence Number"                               
             DEFVAL  { 0 }                                                      
             ::= { ibmTcpipMvsTcpConnEntry 30 }                                 
                                                                                
          ibmMvsTcpConnSendMSS OBJECT-TYPE                                      
             SYNTAX   Integer32                                                 
             MAX-ACCESS   read-only                                             
             STATUS   current                                                   
             DESCRIPTION                                                        
                "Maximum Segment Size we can send"                              
             DEFVAL  { 0 }                                                      
             ::= { ibmTcpipMvsTcpConnEntry 31 }                                 
                                                                                
          ibmMvsTcpConnSndWl1 OBJECT-TYPE                                       
             SYNTAX   Integer32                                                 
             MAX-ACCESS   read-only                                             
             STATUS   current                                                   
             DESCRIPTION                                                        
                "Sequence of last window"                                       
             DEFVAL  { 0 }                                                      
             ::= { ibmTcpipMvsTcpConnEntry 32 }                                 
                                                                                
          ibmMvsTcpConnSndWl2 OBJECT-TYPE                                       
             SYNTAX   Integer32                                                 
             MAX-ACCESS   read-only                                             
             STATUS   current                                                   
             DESCRIPTION                                                        
                "Ack of last window"                                            
             DEFVAL  { 0 }                                                      
             ::= { ibmTcpipMvsTcpConnEntry 33 }                                 
                                                                                
          ibmMvsTcpConnSndWnd OBJECT-TYPE                                       
             SYNTAX   Integer32                                                 
             MAX-ACCESS   read-only                                             
             STATUS   current                                                   
             DESCRIPTION                                                        
                "Send Window size"                                              
             DEFVAL  { 0 }                                                      
             ::= { ibmTcpipMvsTcpConnEntry 34 }                                 
                                                                                
          ibmMvsTcpConnPendTcpRecv OBJECT-TYPE                                  
             SYNTAX   Integer32                                                 
             MAX-ACCESS   read-only                                             
             STATUS   current                                                   
             DESCRIPTION                                                        
                "TCP non_block read flag"                                       
             DEFVAL  { 0 }                                                      
             ::= { ibmTcpipMvsTcpConnEntry 35 }                                 
                                                                                
          ibmMvsTcpConnRcvBufSize OBJECT-TYPE                                   
             SYNTAX   Integer32                                                 
             MAX-ACCESS   read-only                                             
             STATUS   current                                                   
             DESCRIPTION                                                        
                "Receive buffer size"                                           
             DEFVAL  { 0 }                                                      
             ::= { ibmTcpipMvsTcpConnEntry 36 }                                 
                                                                                
          ibmMvsTcpConnResourceName OBJECT-TYPE                                 
             SYNTAX   DisplayString (SIZE(0..8))                                
             MAX-ACCESS   read-only                                             
             STATUS   current                                                   
             DESCRIPTION                                                        
                "Resource Name is the text identification of this               
                 resource. It represents the user the openned the               
                 socket and is updated again doing the bind                     
                 processing."                                                   
             ::= { ibmTcpipMvsTcpConnEntry 37 }                                 
                                                                                
          ibmMvsTcpConnSubtask OBJECT-TYPE                                      
             SYNTAX   Integer32                                                 
             MAX-ACCESS   read-only                                             
             STATUS   current                                                   
             DESCRIPTION                                                        
                "The subtask ID represents task that openned the                
                 socket and is updated again during bind                        
                 processing. It is actually the TCB address."                   
             DEFVAL  { 0 }                                                      
             ::= { ibmTcpipMvsTcpConnEntry 38 }                                 
                                                                                
          ibmMvsTcpConnResourceId OBJECT-TYPE                                   
             SYNTAX   Integer32                                                 
             MAX-ACCESS   read-only                                             
             STATUS   current                                                   
             DESCRIPTION                                                        
                "Resource ID is the numeric identification of this              
                 resource."                                                     
             DEFVAL  { 0 }                                                      
             ::= { ibmTcpipMvsTcpConnEntry 39 }                                 
                                                                                
          ibmMvsTcpConnSockOpt OBJECT-TYPE                                      
             SYNTAX   OCTET STRING (SIZE(1))                                    
             MAX-ACCESS   read-only                                             
             STATUS   current                                                   
             DESCRIPTION                                                        
                "flag for socket options (1 byte hex valuel)                    
                 -bit(1) = Sockets SO_REUSEADDR option                          
                 -bit(2) = SO_OOBINLINE option                                  
                 -bit(3) = SO_LINGER option                                     
                 -bit(4) = T_MSGDONTROUTE                                       
                 -bit(5) = No delay (Nagle off) option                          
                 -bit(6) = SO_Keepalive option                                  
                 -bit(7) = Allow multiple binds to same port (pascal)           
                 -bit(8) = <reserved>"                                          
             ::= { ibmTcpipMvsTcpConnEntry 40 }                                 
                                                                                
          ibmMvsTcpConnTcpTimer OBJECT-TYPE                                     
             SYNTAX   Integer32                                                 
             MAX-ACCESS   read-only                                             
             STATUS   current                                                   
             DESCRIPTION                                                        
                "flag for TCP timers (1 byte hex valuel)                        
                 -bit(1) = currently timing round trip                          
                 -bit(2) = currently timing rexmt                               
                 -bit(3) = currently timing window probe                        
                 -bit(4) = Dally timer currently set                            
                 -bit(5) = max Seg Lifetime timer set                           
                 -bit(6) = curretly timing linger                               
                 -bit(7) = currently timing keep alive                          
                 -bit(8) = <reserved>"                                          
             DEFVAL  { 0 }                                                      
             ::= { ibmTcpipMvsTcpConnEntry 41 }                                 
                                                                                
          ibmMvsTcpConnTcpSig OBJECT-TYPE                                       
             SYNTAX   Integer32                                                 
             MAX-ACCESS   read-only                                             
             STATUS   current                                                   
             DESCRIPTION                                                        
                "1 byte hex flag for TCP signals                                
                -bit(1) = Signal urgent data                                    
                -bit(2) = Signal normal data                                    
                -bit(3) = Signal timing finwait2                                
                -bit(4) = Signal timing connection                              
                -bit(5) = <reserved>                                            
                -bit(6) = <reserved>                                            
                -bit(7) = <reserved>                                            
                -bit(8) = Push data out"                                        
             DEFVAL  { 0 }                                                      
             ::= { ibmTcpipMvsTcpConnEntry 42 }                                 
                                                                                
          ibmMvsTcpConnTcpSel OBJECT-TYPE                                       
             SYNTAX   Integer32                                                 
             MAX-ACCESS   read-only                                             
             STATUS   current                                                   
             DESCRIPTION                                                        
                "TCP select flag byte for TCP select conditions.                
                 It is mapped as follows:                                       
                 -bit(1) = Select for read issued                               
                 -bit(2) = Select for write                                     
                 -bit(3) = Select for exception                                 
                 -bit(4) = Active/passive open                                  
                 -bit(5) = Non blocking read                                    
                 -bit(6) = Blocked for writing                                  
                 -bit(7) = <reserved>                                           
                 -bit(8) = <reserved>"                                          
             DEFVAL  { 0 }                                                      
             ::= { ibmTcpipMvsTcpConnEntry 43 }                                 
                                                                                
          ibmMvsTcpConnRttSeq OBJECT-TYPE                                       
             SYNTAX   Integer32                                                 
             MAX-ACCESS   read-only                                             
             STATUS   current                                                   
             DESCRIPTION                                                        
                "4 byte value for the TCP sequence number"                      
             DEFVAL  { 0 }                                                      
             ::= { ibmTcpipMvsTcpConnEntry 44 }                                 
                                                                                
          ibmMvsTcpConnBackoffCount OBJECT-TYPE                                 
             SYNTAX   Integer32                                                 
             MAX-ACCESS   read-only                                             
             STATUS   current                                                   
             DESCRIPTION                                                        
                "The value of this object will always be zero since             
                 it currently isn't reported."                                  
             DEFVAL  { 0 }                                                      
             ::= { ibmTcpipMvsTcpConnEntry 45 }                                 
                                                                                
          ibmMvsTcpConnTcpDet OBJECT-TYPE                                       
             SYNTAX   OCTET STRING (SIZE(1))                                    
             MAX-ACCESS   read-only                                             
             STATUS   current                                                   
             DESCRIPTION                                                        
                "This flag will hold special TCP protocol                       
                 conditions:                                                    
                 - bit(1) = Delay Acks requested on PORT/PORTRANGE              
                 - bit(2) = Delay Acks requested on GATEWAY                     
                 - bit(3) = Use default round trip parms                        
                 - bit(4) = Connection is one hop away                          
                 - bit(5) = Optimal max segment size request on                 
                            PORT/PORTRANGE                                      
                 - bit(3) = <reserved>"                                         
             ::= { ibmTcpipMvsTcpConnEntry 46 }                                 
                                                                                
          ibmMvsTcpConnTcpPol OBJECT-TYPE                                       
             SYNTAX   OCTET STRING (SIZE(1))                                    
             MAX-ACCESS   read-only                                             
             STATUS   current                                                   
             DESCRIPTION                                                        
                "This flag will indicates the following  TCP                    
                 poll conditions:                                               
                 - bit(1) = poll priority                                       
                 - bit(2) = poll write priority                                 
                 - bit(3) = poll write normal/out                               
                 - bit(4) = poll read priority                                  
                 - bit(5) = poll read normal                                    
                 - bit(6) = poll hang up                                        
                 - bit(7) = poll error                                          
                 - bit(8) = <reserved>"                                         
             ::= { ibmTcpipMvsTcpConnEntry 47 }                                 
                                                                                
          ibmMvsTcpConnTargetAppl OBJECT-TYPE                                   
             SYNTAX   DisplayString (SIZE(0..8))                                
             MAX-ACCESS   read-only                                             
             STATUS   current                                                   
             DESCRIPTION                                                        
                "When the corresponding TCP connection is for a                 
                 3172 Telnet session then this object contains the              
                 Target VTAM Application name."                                 
             ::= { ibmTcpipMvsTcpConnEntry 48 }                                 
                                                                                
          ibmMvsTcpConnLuName OBJECT-TYPE                                       
             SYNTAX   DisplayString (SIZE(0..8))                                
             MAX-ACCESS   read-only                                             
             STATUS   current                                                   
             DESCRIPTION                                                        
                "When the corresponding TCP connection is for a                 
                 3172 Telnet session then this object contains the              
                 VTAM LU name."                                                 
             ::= { ibmTcpipMvsTcpConnEntry 49 }                                 
                                                                                
          ibmMvsTcpConnClientUserId OBJECT-TYPE                                 
             SYNTAX   DisplayString (SIZE(0..8))                                
             MAX-ACCESS   read-only                                             
             STATUS   current                                                   
             DESCRIPTION                                                        
                "When the corresponding TCP connection is for a                 
                 3172 Telnet session then this object contains the              
                 Client's userid."                                              
             ::= { ibmTcpipMvsTcpConnEntry 50 }                                 
                                                                                
          ibmMvsTcpConnLogMode OBJECT-TYPE                                      
             SYNTAX   DisplayString (SIZE(0..8))                                
             MAX-ACCESS   read-only                                             
             STATUS   current                                                   
             DESCRIPTION                                                        
                "When the corresponding TCP connection is for a                 
                 3172 Telnet session then this object contains the              
                 LOG Mode."                                                     
             ::= { ibmTcpipMvsTcpConnEntry 51 }                                 
                                                                                
          ibmMvsTcpConnProto OBJECT-TYPE                                        
             SYNTAX   OCTET STRING (SIZE(1))                                    
             MAX-ACCESS   read-only                                             
             STATUS   current                                                   
             DESCRIPTION                                                        
                "This flag will indicates the following Telnet modes:           
                 -bit(1 - 5) = <reserved>                                       
                 -bit(6)     = TN3270 mode                                      
                 -bit(7)     = TN3270E mode                                     
                 -bit(8)     = line mode"                                       
            ::= { ibmTcpipMvsTcpConnEntry 52 }                                  
                                                                                
          ibmMvsTcpConnDupacks OBJECT-TYPE                                      
             SYNTAX   Integer32                                                 
             MAX-ACCESS   read-only                                             
             STATUS   current                                                   
             DESCRIPTION                                                        
                "Number of duplicate ACKs received for this                     
                 connection."                                                   
             DEFVAL  { 0 }                                                      
             ::= { ibmTcpipMvsTcpConnEntry 53 }                                 
                                                                                
          ibmMvsTcpConnOptMaxSegmentSize OBJECT-TYPE                            
             SYNTAX   Integer32                                                 
             MAX-ACCESS   read-only                                             
             STATUS   current                                                   
             DESCRIPTION                                                        
                "Optimal maximum segment size. The range of this                
                 value is from 0 to 65535."                                     
             DEFVAL  { 0 }                                                      
             ::= { ibmTcpipMvsTcpConnEntry 54 }                                 
                                                                                
 ---------------------------------------------------------------------          
 -- ibmTcpipMvsUdpGroup                                                         
 ---------------------------------------------------------------------          
                                                                                
     ibmTcpipMvsUdpTable OBJECT-TYPE                                            
     SYNTAX SEQUENCE OF IbmTcpipMvsUdpEntry                                     
     MAX-ACCESS not-accessible                                                  
     STATUS current                                                             
     DESCRIPTION                                                                
          "Extends udp table to support gateway semantic."                      
     ::= { ibmTcpipMvsUdpGroup 1 }                                              
                                                                                
     ibmTcpipMvsUdpEntry OBJECT-TYPE                                            
     SYNTAX IbmTcpipMvsUdpEntry                                                 
     MAX-ACCESS not-accessible                                                  
     STATUS current                                                             
     DESCRIPTION                                                                
          "Descibes a particular udp entry."                                    
     AUGMENTS { udpEntry }                                                      
     ::= { ibmTcpipMvsUdpTable 1 }                                              
                                                                                
     IbmTcpipMvsUdpEntry ::=                                                    
          SEQUENCE                                                              
          {                                                                     
          ibmMvsUdpLastAct        TimeTicks,                                    
          ibmMvsUdpTos            TypeOfService,                                
          ibmMvsUdpIpOpts         OCTET STRING,                                 
          ibmMvsUdpDgramIn        Integer32,                                    
          ibmMvsUdpBytesIn        Integer32,                                    
          ibmMvsUdpDgramOut       Integer32,                                    
          ibmMvsUdpBytesOut       Integer32,                                    
          ibmMvsUdpResourceName   DisplayString,                                
          ibmMvsUdpSubtask        Integer32,                                    
          ibmMvsUdpResourceId     Integer32,                                    
          ibmMvsUdpSockOpt        OCTET STRING,                                 
          ibmMvsUdpSendLim        Integer32,                                    
          ibmMvsUdpRecvLim        Integer32,                                    
          ibmMvsUdpEntryState     INTEGER                                       
          }                                                                     
                                                                                
     ibmMvsUdpLastAct OBJECT-TYPE                                               
        SYNTAX   TimeTicks                                                      
        MAX-ACCESS   read-only                                                  
        STATUS   current                                                        
        DESCRIPTION                                                             
           "The amount of time that has elapsed since the corresponding         
            entry has had any activity. Measured in hundreds of                 
            seconds."                                                           
        DEFVAL  { 0 }                                                           
        ::= { ibmTcpipMvsUdpEntry 1 }                                           
                                                                                
     ibmMvsUdpTos OBJECT-TYPE                                                   
        SYNTAX   TypeOfService                                                  
        MAX-ACCESS   read-only                                                  
        STATUS   current                                                        
        DESCRIPTION                                                             
           "The type of service in effect for this entry. Currently,            
            not supported and will return a zero when retreived."               
        DEFVAL  { 0 }                                                           
        ::= { ibmTcpipMvsUdpEntry 2 }                                           
                                                                                
     ibmMvsUdpIpOpts OBJECT-TYPE                                                
        SYNTAX   OCTET STRING (SIZE(40))                                        
        MAX-ACCESS   read-only                                                  
        STATUS   current                                                        
        DESCRIPTION                                                             
           "IP Options (see RFC 791)"                                           
        ::= { ibmTcpipMvsUdpEntry 3 }                                           
                                                                                
     ibmMvsUdpDgramIn OBJECT-TYPE                                               
        SYNTAX   Integer32                                                      
        MAX-ACCESS   read-only                                                  
        STATUS   current                                                        
        DESCRIPTION                                                             
           "Number of received datagrams."                                      
        DEFVAL  { 0 }                                                           
        ::= { ibmTcpipMvsUdpEntry 4 }                                           
                                                                                
     ibmMvsUdpBytesIn OBJECT-TYPE                                               
        SYNTAX   Integer32                                                      
        MAX-ACCESS   read-only                                                  
        STATUS   current                                                        
        DESCRIPTION                                                             
           "Number of bytes received."                                          
        DEFVAL  { 0 }                                                           
        ::= { ibmTcpipMvsUdpEntry 5 }                                           
                                                                                
     ibmMvsUdpDgramOut OBJECT-TYPE                                              
        SYNTAX   Integer32                                                      
        MAX-ACCESS   read-only                                                  
        STATUS   current                                                        
        DESCRIPTION                                                             
           "Number of send datagrams."                                          
        DEFVAL  { 0 }                                                           
        ::= { ibmTcpipMvsUdpEntry 6 }                                           
                                                                                
     ibmMvsUdpBytesOut OBJECT-TYPE                                              
        SYNTAX   Integer32                                                      
        MAX-ACCESS   read-only                                                  
        STATUS   current                                                        
        DESCRIPTION                                                             
           "Number of bytes sent."                                              
        DEFVAL  { 0 }                                                           
        ::= { ibmTcpipMvsUdpEntry 7 }                                           
                                                                                
     ibmMvsUdpResourceName OBJECT-TYPE                                          
        SYNTAX   DisplayString (SIZE(0..8))                                     
        MAX-ACCESS   read-only                                                  
        STATUS   current                                                        
        DESCRIPTION                                                             
           "Resource Name is the text identification of this                    
            resource. It represents the ?itName value of the                    
            associating resource's relationship with the UDP                    
            Stack."                                                             
        ::= { ibmTcpipMvsUdpEntry 8 }                                           
                                                                                
     ibmMvsUdpSubtask OBJECT-TYPE                                               
        SYNTAX   Integer32                                                      
        MAX-ACCESS   read-only                                                  
        STATUS   current                                                        
        DESCRIPTION                                                             
           "4 bytes hex decimal"                                                
        DEFVAL  { 0 }                                                           
        ::= { ibmTcpipMvsUdpEntry 9 }                                           
                                                                                
     ibmMvsUdpResourceId OBJECT-TYPE                                            
        SYNTAX   Integer32                                                      
        MAX-ACCESS   read-only                                                  
        STATUS   current                                                        
        DESCRIPTION                                                             
           "Resource ID is the numeric identification of this                   
            resource."                                                          
        DEFVAL  { 0 }                                                           
        ::= { ibmTcpipMvsUdpEntry 10 }                                          
                                                                                
     ibmMvsUdpSockOpt OBJECT-TYPE                                               
        SYNTAX   OCTET STRING (SIZE(1))                                         
        MAX-ACCESS   read-only                                                  
        STATUS   current                                                        
        DESCRIPTION                                                             
          "flag for socket options (1 byte hex valuel)                          
          -bit(1) = allow broadcast address                                     
          -bit(2) = allow loopback of datagrams                                 
          -bit(3) = bypass normal routing                                       
          -bit(4) = forward ICMP message (Pascal)                               
          -bit(5) = <reserved>                                                  
          -bit(6) = <reserved>                                                  
          -bit(7) = <reserved>                                                  
          -bit(8) = <reserved>"                                                 
        ::= { ibmTcpipMvsUdpEntry 11 }                                          
                                                                                
     ibmMvsUdpSendLim OBJECT-TYPE                                               
        SYNTAX   Integer32                                                      
        MAX-ACCESS   read-only                                                  
        STATUS   current                                                        
        DESCRIPTION                                                             
           "maximum transmit datagram size "                                    
        DEFVAL  { 0 }                                                           
        ::= { ibmTcpipMvsUdpEntry 12 }                                          
                                                                                
     ibmMvsUdpRecvLim OBJECT-TYPE                                               
        SYNTAX   Integer32                                                      
        MAX-ACCESS   read-only                                                  
        STATUS   current                                                        
        DESCRIPTION                                                             
           "maximum received datagram size"                                     
        DEFVAL  { 0 }                                                           
        ::= { ibmTcpipMvsUdpEntry 13 }                                          
                                                                                
     ibmMvsUdpEntryState OBJECT-TYPE                                            
        SYNTAX   INTEGER   {                                                    
                              active(1),                                        
                              delete(2)                                         
                           }                                                    
        MAX-ACCESS   read-write                                                 
        STATUS   current                                                        
        DESCRIPTION                                                             
           "A entry's state will always be active unless it is                  
            to be deleted. This is accomplished by setting this                 
            object to delete. A set of active is invalid."                      
        DEFVAL  { active }                                                      
        ::= { ibmTcpipMvsUdpEntry 14 }                                          
                                                                                
 ---------------------------------------------------------------------          
 -- Notifications if any                                                        
 --                                                                             
 ---------------------------------------------------------------------          
     ibmMvsAtmOsasfAtmPvcCreate NOTIFICATION-TYPE                               
        OBJECTS {                                                               
           ibmMvsAtmOsasfPvcName                                                
        }                                                                       
        STATUS  current                                                         
        DESCRIPTION                                                             
           "This trap is generated when OSA/SF sends a asyn                     
            notification to the TCP/IP DPI Subagent that a                      
            PVC was created for a given OSA Port. This                          
            notification contains the corresponding                             
            ibmMvsAtmOsasfPortName instance. Representation                     
            of this will contain the port's (aal5 layer interface)              
            'ifIndex.pvcNameOctetCount.pvcNameInASCIINvt'."                     
        ::= { ibmTCPIPmvsMIBTraps 1 }                                           
                                                                                
     ibmMvsAtmOsasfAtmPvcDelete NOTIFICATION-TYPE                               
        OBJECTS {                                                               
           ibmMvsAtmOsasfPvcName                                                
        }                                                                       
        STATUS  current                                                         
        DESCRIPTION                                                             
           "This trap is generated when OSA/SF sends a asyn                     
            notification to the TCP/IP DPI Subagent that a                      
            PVC was deleted for a given OSA Port. This                          
            notification contains the corresponding                             
            ibmMvsAtmOsasfPortName instance. Representation                     
            of this will contain the port's (aal5 layer interface)              
            'ifIndex.pvcNameOctetCount.pvcNameInASCIINvt'."                     
        ::= { ibmTCPIPmvsMIBTraps 2 }                                           
                                                                                
                                                                                
 ---------------------------------------------------------------------          
 -- Conformance information                                                     
 -- Compliance statements                                                       
 ---------------------------------------------------------------------          
                                                                                
 ibmTCPIPmvsCompliances OBJECT IDENTIFIER ::= { ibmTCPIPmvsConformance 1 }      
 ibmTCPIPmvsGroups      OBJECT IDENTIFIER ::= { ibmTCPIPmvsConformance 2 }      
                                                                                
 ---------------------------------------------------------------------          
 -- Compliance statements                                                       
 ---------------------------------------------------------------------          
 ibmTCPIPmvsCompliance MODULE-COMPLIANCE                                        
    STATUS  current                                                             
    DESCRIPTION                                                                 
            "The compliance statement for the TCP/IP for MVS                    
            product."                                                           
    MODULE  -- this module                                                      
        MANDATORY-GROUPS {                                                      
                           ibmTCPIPmvsPingGroup,                                
                           ibmTCPIPmvsSystemGroup2,                             
                           ibmTCPIPmvsTcpGroup2,                                
                           ibmTCPIPmvsUdpGroup,                                 
                           ibmTCPIPmvsInterfacesGroup,                          
                           ibmTCPIPmvsPortGroup,                                
                           ibmTCPIPmvsRoutingGroup                              
                         }                                                      
        GROUP  ibmTCPIPmvsAtmSupportGroup2                                      
        DESCRIPTION                                                             
            "The ATM Support Group of objects is only present if                
              ATMENABLED was selected on the SACONFIG statement                 
              in a TCP/IP PROFILE that was used to configure                    
              TCP/IP. In addition, one or more ATM Device and Links             
              must be defined."                                                 
        GROUP  ibmTCPIPmvsAtmNotificationGroup                                  
           DESCRIPTION                                                          
                "OSA ATM Management notifications"                              
        GROUP    ibmTCPIPmvsAtmLeGroup                                          
        DESCRIPTION                                                             
            "The ATM LAN Emulation Group consists of objects that               
              provide information if a ATM Port was configured                  
              to run in LAN Emulation mode."                                    
    ::= { ibmTCPIPmvsCompliances 1 }                                            
                                                                                
 ---------------------------------------------------------------------          
 -- MIB groupings                                                               
 ---------------------------------------------------------------------          
 ibmTCPIPmvsPingGroup OBJECT-GROUP                                              
   OBJECTS {                                                                    
               ibmMvsRPingResponseTime                                          
              }                                                                 
   STATUS  current                                                              
   DESCRIPTION  " "                                                             
    ::= { ibmTCPIPmvsGroups 1 }                                                 
                                                                                
ibmTCPIPmvsSystemGroup2 OBJECT-GROUP                                            
   OBJECTS {                                                                    
                ibmMvsSubagentCacheTime,                                        
                ibmMvsIgnoreRedirect,                                           
                ibmMvsArpCacheTimeout,                                          
                ibmMvsTcpKeepAliveTimer,                                        
                ibmMvsTcpReceiveBufferSize,                                     
                ibmMvsTcpSendBufferSize,                                        
                ibmMvsUdpChecksum,                                              
                ibmMvsIplDateAndTime,                                           
                ibmMvsNoUdpQueueLimit,                                          
                ibmMvsSoMaxConn,                                                
                ibmMvsTcpipProcname,                                            
                ibmMvsTcpipAsid,                                                
                ibmMvsSourceVipaEnabled,                                        
                ibmMvsOsasfSysplexName,                                         
                ibmMvsOsasfHostName,                                            
                ibmMvsOsasfProductVersion,                                      
                ibmMvsPrimaryInterfaceIfIndex,                                  
                ibmMvsIpMaxReassemblySize,                                      
                ibmMvsTcpRestrictLowPorts,                                      
                ibmMvsUdpRestrictLowPorts,                                      
                ibmMvsUdpSendBufferSize,                                        
                ibmMvsUdpRecvBufferSize,                                        
                ibmMvsTcpipStatisticsEnabled,                                   
                ibmMvsFirewallEnabled,                                          
                ibmMvsMaximumRetransmitTime,                                    
                ibmMvsMinimumRetransmitTime,                                    
                ibmMvsRoundTripGain,                                            
                ibmMvsVarianceMultiplier,                                       
                ibmMvsVarianceGain,                                             
                ibmMvsSendGarbageEnabled                                        
              }                                                                 
   STATUS  current                                                              
   DESCRIPTION                                                                  
           " "                                                                  
    ::= { ibmTCPIPmvsGroups 13 }                                                
                                                                                
ibmTCPIPmvsTcpGroup2 OBJECT-GROUP                                               
   OBJECTS {                                                                    
               ibmMvsTcpConnLastActivity,                                       
               ibmMvsTcpConnBytesIn,                                            
               ibmMvsTcpConnBytesOut,                                           
               ibmMvsTcpConnActiveOpen,                                         
               ibmMvsTcpConnIpTos,                                              
               ibmMvsTcpConnOptions,                                            
               ibmMvsTcpConnOutBuffered,                                        
               ibmMvsTcpConnUsrSndNxt,                                          
               ibmMvsTcpConnSndNxt,                                             
               ibmMvsTcpConnSndUna,                                             
               ibmMvsTcpConnOutgoingPush,                                       
               ibmMvsTcpConnOutgoingUrg,                                        
               ibmMvsTcpConnOutgoingWinSeq,                                     
               ibmMvsTcpConnInBuffered,                                         
               ibmMvsTcpConnRcvNxt,                                             
               ibmMvsTcpConnUsrRcvNxt,                                          
               ibmMvsTcpConnIncomingPush,                                       
               ibmMvsTcpConnIncomingUrg,                                        
               ibmMvsTcpConnIncomingWinSeq,                                     
               ibmMvsTcpConnReXmt,                                              
               ibmMvsTcpConnMaxSndWnd,                                          
               ibmMvsTcpConnReXmtCount,                                         
               ibmMvsTcpConnCongestionWnd,                                      
               ibmMvsTcpConnSSThresh,                                           
               ibmMvsTcpConnRoundTripTime,                                      
               ibmMvsTcpConnRoundTripVariance,                                  
               ibmMvsTcpConnInitSndSeq,                                         
               ibmMvsTcpConnInitRcvSeq,                                         
               ibmMvsTcpConnSendMSS,                                            
               ibmMvsTcpConnSndWl1,                                             
               ibmMvsTcpConnSndWl2,                                             
               ibmMvsTcpConnSndWnd,                                             
               ibmMvsTcpConnPendTcpRecv,                                        
               ibmMvsTcpConnRcvBufSize,                                         
               ibmMvsTcpConnResourceName,                                       
               ibmMvsTcpConnSubtask,                                            
               ibmMvsTcpConnResourceId,                                         
               ibmMvsTcpConnSockOpt,                                            
               ibmMvsTcpConnTcpTimer,                                           
               ibmMvsTcpConnTcpSig,                                             
               ibmMvsTcpConnTcpSel,                                             
               ibmMvsTcpConnRttSeq,                                             
               ibmMvsTcpConnBackoffCount,                                       
               ibmMvsTcpConnTcpDet,                                             
               ibmMvsTcpConnTcpPol,                                             
               ibmMvsTcpConnTargetAppl,                                         
               ibmMvsTcpConnLuName,                                             
               ibmMvsTcpConnClientUserId,                                       
               ibmMvsTcpConnLogMode,                                            
               ibmMvsTcpConnProto,                                              
               ibmMvsTcpConnDupacks,                                            
               ibmMvsTcpConnOptMaxSegmentSize                                   
              }                                                                 
   STATUS  current                                                              
   DESCRIPTION                                                                  
           "Defines the objects that are augmented to the tcpConnTable"         
    ::= { ibmTCPIPmvsGroups 12 }                                                
                                                                                
ibmTCPIPmvsUdpGroup OBJECT-GROUP                                                
   OBJECTS {                                                                    
               ibmMvsUdpLastAct,                                                
               ibmMvsUdpTos,                                                    
               ibmMvsUdpIpOpts,                                                 
               ibmMvsUdpDgramIn,                                                
               ibmMvsUdpBytesIn,                                                
               ibmMvsUdpDgramOut,                                               
               ibmMvsUdpBytesOut,                                               
               ibmMvsUdpResourceName,                                           
               ibmMvsUdpSubtask,                                                
               ibmMvsUdpResourceId,                                             
               ibmMvsUdpSockOpt,                                                
               ibmMvsUdpSendLim,                                                
               ibmMvsUdpRecvLim,                                                
               ibmMvsUdpEntryState                                              
              }                                                                 
   STATUS  current                                                              
   DESCRIPTION                                                                  
           "This group defines those objects that are argumented to             
             a udp listen table entry."                                         
    ::= { ibmTCPIPmvsGroups 4 }                                                 
                                                                                
 ibmTCPIPmvsAtmSupportGroup2 OBJECT-GROUP                                       
   OBJECTS {                                                                    
               ibmMvsAtmOsasfChannelNumber,                                     
               ibmMvsAtmOsasfChannelType,                                       
               ibmMvsAtmOsasfChannelSubType,                                    
               ibmMvsAtmOsasfChannelMode,                                       
               ibmMvsAtmOsasfChannelHwModel,                                    
               ibmMvsAtmOsasfChannelState,                                      
               ibmMvsAtmOsasfChannelShared,                                     
               ibmMvsAtmOsasfChannelNumPorts,                                   
               ibmMvsAtmOsasfChannelDeterNodeDesc,                              
               ibmMvsAtmOsasfChannelControlUnitNumber,                          
               ibmMvsAtmOsasfChannelCodeLevel,                                  
               ibmMvsAtmOsasfChannelEcLevel,                                    
               ibmMvsAtmOsasfChannelCurLparName,                                
               ibmMvsAtmOsasfChannelCurLparNum,                                 
               ibmMvsAtmOsasfChannelManParnName,                                
               ibmMvsAtmOsasfChannelManParnNum,                                 
               ibmMvsAtmOsasfChannelDate,                                       
               ibmMvsAtmOsasfChannelTime,                                       
               ibmMvsAtmOsasfChannelFlashLevel,                                 
               ibmMvsAtmOsasfChannelVtamId,                                     
               ibmMvsAtmOsasfPortNumber,                                        
               ibmMvsAtmOsasfPortType,                                          
               ibmMvsAtmOsasfPortHardwareState,                                 
               ibmMvsAtmOsasfPortMediaType,                                     
               ibmMvsAtmOsasfPortUniType,                                       
               ibmMvsAtmOsasfPortUniVersion,                                    
               ibmMvsAtmOsasfPortNetPrefix,                                     
               ibmMvsAtmOsasfPortNetPrefixPrefix,                               
               ibmMvsAtmOsasfPortNetPrefixStatus,                               
               ibmMvsAtmOsasfPortCodeLoadStatus,                                
               ibmMvsAtmOsasfPortMacAddrBurntIn,                                
               ibmMvsAtmOsasfPortMacAddrActive,                                 
               ibmMvsAtmOsasfPortMaxPcmConnections,                             
               ibmMvsAtmOsasfPortPcmName,                                       
               ibmMvsAtmOsasfPortAAL5InPackets,                                 
               ibmMvsAtmOsasfPortAAL5OutPackets,                                
               ibmMvsAtmOsasfPortIpAddress,                                     
               ibmMvsAtmOsasfPvcName,                                           
               ibmMvsAtmOsasfPvcBestEffort,                                     
               ibmMvsAtmOsasfPvcFwdPeakCellRate,                                
               ibmMvsAtmOsasfPvcBwdPeakCellRate,                                
               ibmMvsAtmOsasfPvcFwdsustainCellRate,                             
               ibmMvsAtmOsasfPvcBwdsustainCellRate,                             
               ibmMvsAtmOsasfPvcFwdCellBurstSize,                               
               ibmMvsAtmOsasfPvcBwdCellBurstSize,                               
               ibmMvsAtmOsasfPvcVpi,                                            
               ibmMvsAtmOsasfPvcVci,                                            
               ibmMvsAtmOsasfPvcFwdMaxAal5PduSize,                              
               ibmMvsAtmOsasfPvcBwdMaxAal5PduSize                               
              }                                                                 
   STATUS  current                                                              
   DESCRIPTION                                                                  
           "This group comprises those objects that are related                 
             to atm support."                                                   
    ::= { ibmTCPIPmvsGroups 14 }                                                
                                                                                
   ibmTCPIPmvsAtmNotificationGroup NOTIFICATION-GROUP                           
   NOTIFICATIONS {                                                              
                ibmMvsAtmOsasfAtmPvcCreate,                                     
                ibmMvsAtmOsasfAtmPvcDelete                                      
               }                                                                
   STATUS  current                                                              
   DESCRIPTION                                                                  
           "This group comprises those objects that are related                 
             to atm support."                                                   
   ::= { ibmTCPIPmvsGroups 7 }                                                  
                                                                                
   ibmTCPIPmvsInterfacesGroup OBJECT-GROUP                                      
   OBJECTS {                                                                    
                ibmMvsDeviceType,                                               
                ibmMvsDeviceBaseNumber,                                         
                ibmMvsDeviceIoBufferSize,                                       
                ibmMvsDeviceAutoRestart,                                        
                ibmMvsDeviceNetmanEnabled,                                      
                ibmMvsDeviceHostClawName,                                       
                ibmMvsDeviceWorkstationClawName,                                
                ibmMvsDeviceReadBuffers,                                        
                ibmMvsDeviceReadSize,                                           
                ibmMvsDeviceWriteBuffers,                                       
                ibmMvsDeviceWriteSize,                                          
                ibmMvsDeviceProcname,                                           
                ibmMvsDeviceIncomingSvcEnabled,                                 
                ibmMvsDeviceLuName,                                             
                ibmMvsLinkType,                                                 
                ibmMvsLinkDeviceIndex,                                          
                ibmMvsLinkAdapterAddr,                                          
                ibmMvsLinkNumber,                                               
                ibmMvsLinkIbmtrCanonical,                                       
                ibmMvsLinkIbmtrBcast                                            
              }                                                                 
   STATUS  current                                                              
   DESCRIPTION                                                                  
           "This group comprises those objects that are related                 
             to interface entries in the IF-MIB."                               
    ::= { ibmTCPIPmvsGroups 8 }                                                 
                                                                                
   ibmTCPIPmvsAtmLeGroup OBJECT-GROUP                                           
   OBJECTS {                                                                    
                ibmMvsAtmSnaLeLlcTi,                                            
                ibmMvsAtmSnaLeLlcT1,                                            
                ibmMvsAtmSnaLeLlcT2,                                            
                ibmMvsAtmSnaleMaxStations,                                      
                ibmMvsAtmSnaLeMaxSaps,                                          
                ibmMvsAtmSnaleMaxIn,                                            
                ibmMvsAtmSnaLeMaxOut,                                           
                ibmMvsAtmSnaLeCrsGroupAddress,                                  
                ibmMvsAtmSnaLeUserData,                                         
                ibmMvsAtmSnaLeClientEnableState,                                
                ibmMvsAtmSnaLeBestEffortPeakRate,                               
                ibmMvsAtmSnaLeMaxLECConnections,                                
                ibmMvsAtmSnaLeTrEnableLoadBalancing,                            
                ibmMvsAtmSnaLeTrLoadBalancing,                                  
                ibmMvsAtmSnaLeTrSessionDelay,                                   
                ibmMvsAtmLecConfigMode,                                         
                ibmMvsAtmLecConfigLanType,                                      
                ibmMvsAtmLecConfigMaxDataFrameSize,                             
                ibmMvsAtmLecConfigLanName,                                      
                ibmMvsAtmLecConfigLesAtmAddress,                                
                ibmMvsAtmLecControlTimeout,                                     
                ibmMvsAtmLecMaxUnknownFrameCount,                               
                ibmMvsAtmLecMaxUnknownFrameTime,                                
                ibmMvsAtmLecVccTimeoutPeriod,                                   
                ibmMvsAtmLecMaxRetryCount,                                      
                ibmMvsAtmLecAgingTime,                                          
                ibmMvsAtmLecForwardDelayTime,                                   
                ibmMvsAtmLecExpectedArpResponseTime,                            
                ibmMvsAtmLecFlushTimeout,                                       
                ibmMvsAtmLecPathSwitchingDelay,                                 
                ibmMvsAtmLecLocalSegmentID,                                     
                ibmMvsAtmLecMulticastSendType,                                  
                ibmMvsAtmLecMulticastSendAvgRate,                               
                ibmMvsAtmLecMulticastSendPeakRate,                              
                ibmMvsAtmLecConnectionCompleteTimer,                            
                ibmMvsAtmLecPrimaryAtmAddress,                                  
                ibmMvsAtmLecID,                                                 
                ibmMvsAtmLecInterfaceState,                                     
                ibmMvsAtmLecLastFailureRespCode,                                
                ibmMvsAtmLecLastFailureState,                                   
                ibmMvsAtmLecProtocol,                                           
                ibmMvsAtmLecVersion,                                            
                ibmMvsAtmLecTopologyChange,                                     
                ibmMvsAtmLecConfigServerAtmAddress,                             
                ibmMvsAtmLecConfigSource,                                       
                ibmMvsAtmLecActualLanType,                                      
                ibmMvsAtmLecActualMaxDataFrameSize,                             
                ibmMvsAtmLecActualLanName,                                      
                ibmMvsAtmLecAtmAddress,                                         
                ibmMvsAtmLecProxyClient,                                        
                ibmMvsAtmLecArpRequestsOut,                                     
                ibmMvsAtmLecArpRequestsIn,                                      
                ibmMvsAtmLecArpRepliesOut,                                      
                ibmMvsAtmLecArpRepliesIn,                                       
                ibmMvsAtmLecControlFramesOut,                                   
                ibmMvsAtmLecControlFramesIn,                                    
                ibmMvsAtmLecSvcFailures,                                        
                ibmMvsAtmLecConfigDirectInterface,                              
                ibmMvsAtmLecConfigDirectVPI,                                    
                ibmMvsAtmLecConfigDirectVCI,                                    
                ibmMvsAtmLecControlDirectInterface,                             
                ibmMvsAtmLecControlDirectVPI,                                   
                ibmMvsAtmLecControlDirectVCI,                                   
                ibmMvsAtmLecControlDistributeInterface,                         
                ibmMvsAtmLecControlDistributeVPI,                               
                ibmMvsAtmLecControlDistributeVCI,                               
                ibmMvsAtmLecMulticastSendInterface,                             
                ibmMvsAtmLecMulticastSendVPI,                                   
                ibmMvsAtmLecMulticastSendVCI,                                   
                ibmMvsAtmLecMulticastFwdInterface,                              
                ibmMvsAtmLecMulticastFwdVPI,                                    
                ibmMvsAtmLecMulticastFwdVCI,                                    
                ibmMvsAtmLecMacAddress                                          
              }                                                                 
   STATUS  current                                                              
   DESCRIPTION                                                                  
           "This group comprises those objects that are related                 
             to ATM LAN Emulation support."                                     
    ::= { ibmTCPIPmvsGroups 9 }                                                 
                                                                                
   ibmTCPIPmvsPortGroup OBJECT-GROUP                                            
   OBJECTS {                                                                    
                ibmMvsPortNumberLow,                                            
                ibmMvsPortNumberHigh,                                           
                ibmMvsPortProtocol,                                             
                ibmMvsPortProcName,                                             
                ibmMvsPortAutoLoggable,                                         
                ibmMvsPortDelayAcks,                                            
                ibmMvsPortOptMaxSegmentSize,                                    
                ibmMvsPortSharePort                                             
             }                                                                  
   STATUS  current                                                              
   DESCRIPTION                                                                  
           "This group comprises those objects that represent the               
             current set of PORT and PORTRANGE definitions                      
             for this TCP/IP instance."                                         
    ::= { ibmTCPIPmvsGroups 10 }                                                
                                                                                
                                                                                
   ibmTCPIPmvsRoutingGroup OBJECT-GROUP                                         
   OBJECTS {                                                                    
                 ibmMvsGatewayMaximumRetransmitTime,                            
                 ibmMvsGatewayMinimumRetransmitTime,                            
                 ibmMvsGatewayRoundTripGain,                                    
                 ibmMvsGatewayVarianceGain,                                     
                 ibmMvsGatewayVarianceMultiplier,                               
                 ibmMvsGatewayDelayAcks                                         
              }                                                                 
   STATUS  current                                                              
   DESCRIPTION                                                                  
           "This group comprises the TCP/IP retransmission parms                
             that are in effect for a locally configured route entry."          
    ::= { ibmTCPIPmvsGroups 11 }                                                
                                                                                
--                                                                              
-- obsolete definitions                                                         
--                                                                              
                                                                                
   ibmTCPIPmvsObsoleteGroup OBJECT-GROUP                                        
   OBJECTS {                                                                    
                ibmSNMPRemPing                                                  
              }                                                                 
   STATUS  obsolete                                                             
   DESCRIPTION                                                                  
           "This group comprises those objects that are obsolete."              
    ::= { ibmTCPIPmvsGroups 6 }                                                 
                                                                                
ibmTCPIPmvsTcpGroup OBJECT-GROUP                                                
   OBJECTS {                                                                    
               ibmMvsTcpConnLastActivity,                                       
               ibmMvsTcpConnBytesIn,                                            
               ibmMvsTcpConnBytesOut,                                           
               ibmMvsTcpConnActiveOpen,                                         
               ibmMvsTcpConnIpTos,                                              
               ibmMvsTcpConnOptions,                                            
               ibmMvsTcpConnOutBuffered,                                        
               ibmMvsTcpConnUsrSndNxt,                                          
               ibmMvsTcpConnSndNxt,                                             
               ibmMvsTcpConnSndUna,                                             
               ibmMvsTcpConnOutgoingPush,                                       
               ibmMvsTcpConnOutgoingUrg,                                        
               ibmMvsTcpConnOutgoingWinSeq,                                     
               ibmMvsTcpConnSendWindowSeq,                                      
               ibmMvsTcpConnSendWindowAck,                                      
               ibmMvsTcpConnInBuffered,                                         
               ibmMvsTcpConnRcvNxt,                                             
               ibmMvsTcpConnUsrRcvNxt,                                          
               ibmMvsTcpConnIncomingPush,                                       
               ibmMvsTcpConnIncomingUrg,                                        
               ibmMvsTcpConnIncomingWinSeq,                                     
               ibmMvsTcpConnReXmt,                                              
               ibmMvsTcpConnMaxSndWnd,                                          
               ibmMvsTcpConnReXmtCount,                                         
               ibmMvsTcpConnCongestionWnd,                                      
               ibmMvsTcpConnSSThresh,                                           
               ibmMvsTcpConnRoundTripTime,                                      
               ibmMvsTcpConnRoundTripVariance,                                  
               ibmMvsTcpConnInitSndSeq,                                         
               ibmMvsTcpConnInitRcvSeq,                                         
               ibmMvsTcpConnSendMSS,                                            
               ibmMvsTcpConnSndWl1,                                             
               ibmMvsTcpConnSndWl2,                                             
               ibmMvsTcpConnSndWnd,                                             
               ibmMvsTcpConnPendTcpRecv,                                        
               ibmMvsTcpConnRcvBufSize,                                         
               ibmMvsTcpConnResourceName,                                       
               ibmMvsTcpConnSubtask,                                            
               ibmMvsTcpConnResourceId,                                         
               ibmMvsTcpConnSockOpt,                                            
               ibmMvsTcpConnTcpTimer,                                           
               ibmMvsTcpConnTcpSig,                                             
               ibmMvsTcpConnTcpSel,                                             
               ibmMvsTcpConnRttSeq,                                             
               ibmMvsTcpConnBackoffCount,                                       
               ibmMvsTcpConnTcpDet,                                             
               ibmMvsTcpConnTcpPol                                              
                        }                                                       
   STATUS  obsolete                                                             
   DESCRIPTION                                                                  
           "Defines the objects that are argumented to the tcpConnTable"        
    ::= { ibmTCPIPmvsGroups 3 }                                                 
                                                                                
ibmTCPIPmvsSystemGroup OBJECT-GROUP                                             
   OBJECTS {                                                                    
                ibmMvsSubagentCacheTime                                         
              }                                                                 
   STATUS  current                                                              
   DESCRIPTION                                                                  
           " "                                                                  
    ::= { ibmTCPIPmvsGroups 2 }                                                 
                                                                                
 ibmTCPIPmvsAtmSupportGroup OBJECT-GROUP                                        
   OBJECTS {                                                                    
               ibmMvsAtmOsasfChannelNumber,                                     
               ibmMvsAtmOsasfChannelType,                                       
               ibmMvsAtmOsasfChannelSubType,                                    
               ibmMvsAtmOsasfChannelMode,                                       
               ibmMvsAtmOsasfChannelHwModel,                                    
               ibmMvsAtmOsasfChannelState,                                      
               ibmMvsAtmOsasfChannelShared,                                     
               ibmMvsAtmOsasfChannelNumPorts,                                   
               ibmMvsAtmOsasfChannelDeterNodeDesc,                              
               ibmMvsAtmOsasfChannelControlUnitNumber,                          
               ibmMvsAtmOsasfChannelCodeLevel,                                  
               ibmMvsAtmOsasfChannelEcLevel,                                    
               ibmMvsAtmOsasfChannelCurLparName,                                
               ibmMvsAtmOsasfChannelCurLparNum,                                 
               ibmMvsAtmOsasfChannelManParnName,                                
               ibmMvsAtmOsasfChannelManParnNum,                                 
               ibmMvsAtmOsasfChannelDate,                                       
               ibmMvsAtmOsasfChannelTime,                                       
               ibmMvsAtmOsasfChannelFlashLevel,                                 
               ibmMvsAtmOsasfChannelVtamId,                                     
               ibmMvsAtmOsasfPortNumber,                                        
               ibmMvsAtmOsasfPortType,                                          
               ibmMvsAtmOsasfPortHardwareState,                                 
               ibmMvsAtmOsasfPortMediaType,                                     
               ibmMvsAtmOsasfPortUniType,                                       
               ibmMvsAtmOsasfPortUniVersion,                                    
               ibmMvsAtmOsasfPortNetPrefix,                                     
               ibmMvsAtmOsasfPortNetPrefixPrefix,                               
               ibmMvsAtmOsasfPortNetPrefixStatus,                               
               ibmMvsAtmOsasfPortCodeLoadStatus,                                
               ibmMvsAtmOsasfPortMacAddrBurntIn,                                
               ibmMvsAtmOsasfPortMacAddrActive,                                 
               ibmMvsAtmOsasfPortMaxPcmConnections,                             
               ibmMvsAtmOsasfPortPcmName,                                       
               ibmMvsAtmOsasfPvcName,                                           
               ibmMvsAtmOsasfPvcBestEffort,                                     
               ibmMvsAtmOsasfPvcFwdPeakCellRate,                                
               ibmMvsAtmOsasfPvcBwdPeakCellRate,                                
               ibmMvsAtmOsasfPvcFwdsustainCellRate,                             
               ibmMvsAtmOsasfPvcBwdsustainCellRate,                             
               ibmMvsAtmOsasfPvcFwdCellBurstSize,                               
               ibmMvsAtmOsasfPvcBwdCellBurstSize,                               
               ibmMvsAtmOsasfPvcVpi,                                            
               ibmMvsAtmOsasfPvcVci,                                            
               ibmMvsAtmOsasfPvcFwdMaxAal5PduSize,                              
               ibmMvsAtmOsasfPvcBwdMaxAal5PduSize                               
              }                                                                 
   STATUS  current                                                              
   DESCRIPTION                                                                  
           "This group comprises those objects that are related                 
             to atm support."                                                   
    ::= { ibmTCPIPmvsGroups 5 }                                                 
                                                                                
END
