-- MIB created 11/13/98 22:12:36, by
--   SMIC (the next generation) version 1.6.29, November 22, 1994.

TN3270E-RT-MIB DEFINITIONS ::= BEGIN

-- From file: "tn3270e-rt.mi2"
-- Compile options "G A T M"

IMPORTS
    Counter32, Gauge32
            FROM SNMPv2-SMI-v1
    OBJECT-TYPE
            FROM RFC-1212
    TRAP-TYPE
            FROM RFC-1215
    RowStatus, DateAndTime, TimeStamp, DisplayString
            FROM SNMPv2-TC-v1
    Tn3270eAddrType, Tn3270eTAddress, tn3270eSrvrConfIndex, 
    tn3270eResMapElementName, tn3270eResMapElementType
            FROM TN3270E-MIB
    snanauMIB
            FROM SNA-NAU-MIB;

tn3270eRtMIB OBJECT IDENTIFIER ::= { snanauMIB 9 }
-- MODULE-IDENTITY
--  LastUpdated
--    9711200000Z
--  OrgName
--    TN3270E Working Group
--  ContactInfo
--    Kenneth White (kennethw@vnet.ibm.com)
--     IBM Corp. - Dept. BRQA/Bldg. 501/G114
--     P.O. Box 12195
--     3039 Cornwallis
--     RTP, NC 27709-2195
--     (919) 254-0102
--    
--     Robert Moore (remoore@us.ibm.com)
--     IBM Corp. - Dept. BRQA/Bldg. 501/G114
--     P.O. Box 12195
--     3039 Cornwallis
--     RTP, NC 27709-2195
--     (919) 254-4436
--  Descr
--    This module defines a portion of the management information
--     base (MIB) that enables monitoring of TN3270 and TN3270E
--     clients' response times by a TN3270E server.

tn3270eRtNotifications OBJECT IDENTIFIER ::= { tn3270eRtMIB 0 }
tn3270eRtObjects OBJECT IDENTIFIER ::= { tn3270eRtMIB 1 }
tn3270eRtConformance OBJECT IDENTIFIER ::= { tn3270eRtMIB 3 }
tn3270eRtGroups OBJECT IDENTIFIER ::= { tn3270eRtConformance 1 }
tn3270eRtCompliances OBJECT IDENTIFIER ::= { tn3270eRtConformance 2 }

tn3270eRtCollCtlTable OBJECT-TYPE
    SYNTAX SEQUENCE OF Tn3270eRtCollCtlEntry
    ACCESS not-accessible
    STATUS mandatory
    DESCRIPTION
        "The response time monitoring collection control table, which
         allows a management application to control the types of
         response time data being collected, and the clients for which
         it is being collected.
        
         This table is indexed by tn3270eSrvrConfIndex, imported from
         the TN3270E-MIB, and by tn3270eRtCollCtlClientGroupName.
         tn3270eSrvrConfIndex indicates within a host which TN3270E
         server an entry applied to.
        
         tn3270eRtCollCtlClientGroupName is equivalent to the
         tn3270eClientGroupName index in the TN3270E-MIB; it identifies
         the collection of IP clients for which response time data
         is being collectedr. The particular IP clients making up the
         collection are identified in the tn3270eClientGroupTable in
         the TN3270E-MIB."
    ::= { tn3270eRtObjects 1 }

tn3270eRtCollCtlEntry OBJECT-TYPE
    SYNTAX Tn3270eRtCollCtlEntry
    ACCESS not-accessible
    STATUS mandatory
    DESCRIPTION
        "Entry in the TN3270E response time monitoring collection
         control table. To handle the case of multiple TN3270E servers
         on the same host, the first index of this table is the
         tn3270eSrvrConfIndex from the TN3270E-MIB."
    INDEX { tn3270eSrvrConfIndex, tn3270eRtCollCtlClientGroupName }
    ::= { tn3270eRtCollCtlTable 1 }

Tn3270eRtCollCtlEntry ::= SEQUENCE {
    tn3270eRtCollCtlClientGroupName DisplayString,
    tn3270eRtCollCtlType OCTET STRING,
    tn3270eRtCollCtlSPeriod UInteger32,
    tn3270eRtCollCtlSPMult UInteger32,
    tn3270eRtCollCtlThreshHigh UInteger32,
    tn3270eRtCollCtlThreshLow UInteger32,
    tn3270eRtCollCtlIdleRate UInteger32,
    tn3270eRtCollCtlBucketBndry1 UInteger32,
    tn3270eRtCollCtlBucketBndry2 UInteger32,
    tn3270eRtCollCtlBucketBndry3 UInteger32,
    tn3270eRtCollCtlBucketBndry4 UInteger32,
    tn3270eRtCollCtlRowStatus RowStatus
    }

tn3270eRtCollCtlClientGroupName OBJECT-TYPE
    SYNTAX DisplayString(SIZE(1..24))
--    Rsyntax OCTET STRING(SIZE(1..24))
    ACCESS not-accessible
    STATUS mandatory
    DESCRIPTION
        "The name of a client group. Membership in a client group is
         specified via the TN3270E-MIB's tn3270eClientGroupTable.
         The index for that table, tn3270eClientGroupName, is
         equivalent to this object; it was not imported because
         doing so results in MIB compiler errors."
    ::= { tn3270eRtCollCtlEntry 1 }

tn3270eRtCollCtlType OBJECT-TYPE
    SYNTAX OCTET STRING(SIZE(2))
    ACCESS read-write
    STATUS mandatory
    DESCRIPTION
        "This object controls what types of response time data to
         collect, whether to summarize the data across the members
         of a client group or keep it individually, whether to
         introduce dynamic definite responses, and whether to
         generate traps.
        
         aggregate(0)          - Aggregate response time data for the
                                 client group as a whole. If this bit is
                                 set to 0, then maintain response time
                                 data separately for each member of the
                                 client group.
         excludeIpComponent(1) - Do not include the IP-network component
                                 in any response times.
         ddr(2)                - Enable dynamic definite response.
         average(3)            - Produce an average response time based
                                 on a specified collection interval.
         buckets(4)            - Maintain tn3270eRtDataBucket values in
                                 a corresponding tn3270eRtDataEntry,
                                 based on the bucket boundaries
                                 specified in the
                                 tn3270eRtDataBucketBndry objects.
         traps(5)              - generate the traps specified in this
                                 MIB module. The tn3270eRtExceeded and
                                 tn3270eRtOkay are generated only if
                                 average(3) is also specified."
    ::= { tn3270eRtCollCtlEntry 2 }

tn3270eRtCollCtlSPeriod OBJECT-TYPE
    SYNTAX UInteger32
--  Units
--    seconds
    ACCESS read-write
    STATUS mandatory
    DESCRIPTION
        "The number of seconds that defines the sample period.
         The actual interval is defined as tn3270eRtCollCtlSPeriod
         times tn3270eRtCollCtlSPMult.
        
         The value of this object is used only if the corresponding
         tn3270eRtCollCtlType has the average(3) setting."
    DEFVAL { 20 }
    ::= { tn3270eRtCollCtlEntry 3 }

tn3270eRtCollCtlSPMult OBJECT-TYPE
    SYNTAX UInteger32
--  Units
--    count
    ACCESS read-write
    STATUS mandatory
    DESCRIPTION
        "The sample period multiplier; this value is multiplied by the
         sample period, tn3270eRtCollCtlSPeriod, to determine the
         collection interval.
        
         The value of this object is used only if the corresponding
         tn3270eRtCollCtlType has the average(3) setting."
    DEFVAL { 30 }
    ::= { tn3270eRtCollCtlEntry 4 }

tn3270eRtCollCtlThreshHigh OBJECT-TYPE
    SYNTAX UInteger32
--  Units
--    seconds
    ACCESS read-write
    STATUS mandatory
    DESCRIPTION
        "The threshold for generating a tn3270eRtExceeded notification,
        signalling that a monitored total response time has exceeded the
        specified limit.  A value of zero for this object suppresses
        generation of this notification.  The value of this object is
        used only if the corresponding tn3270eRtCollCtlType has
        average(3) and traps(5) selected."
    ::= { tn3270eRtCollCtlEntry 5 }

tn3270eRtCollCtlThreshLow OBJECT-TYPE
    SYNTAX UInteger32
--  Units
--    seconds
    ACCESS read-write
    STATUS mandatory
    DESCRIPTION
        "The threshold for generating a tn3270eRtOkay notification,
        signalling that a monitored total response time has fallen below
        the specified limit.  A value of zero for this object suppresses
        generation of this notification.  The value of this object is
        used only if the corresponding tn3270eRtCollCtlType has
        average(3) and traps(5) selected."
    ::= { tn3270eRtCollCtlEntry 6 }

tn3270eRtCollCtlIdleRate OBJECT-TYPE
    SYNTAX UInteger32
--  Units
--    transaction count
    ACCESS read-write
    STATUS mandatory
    DESCRIPTION
        "The value of this object is used to determine whether a sample
         that yields an average response time exceeding the value of
         tn3270eRtCollCtlThreshHigh was a statistically valid one.  If
         the following statement is true, then the sample was
         statistically valid, and so a tn3270eRtExceeded notification
         should be generated:
        
            AvgTransCount * ((AvgRt/ThreshHigh - 1) ** 2) <  IdleRate
        
         This comparison is done only if the corresponding
         tn3270eRtCollCtlType has average(3) and traps(5) selected."
    DEFVAL { 1 }
    ::= { tn3270eRtCollCtlEntry 7 }

tn3270eRtCollCtlBucketBndry1 OBJECT-TYPE
    SYNTAX UInteger32
--  Units
--    tenths of seconds
    ACCESS read-write
    STATUS mandatory
    DESCRIPTION
        "The value of this object defines the range of transaction
         response times counted in the Tn3270eRtDataBucket1 object:
         those less than or equal to this value."
    DEFVAL { 10 }
    ::= { tn3270eRtCollCtlEntry 8 }

tn3270eRtCollCtlBucketBndry2 OBJECT-TYPE
    SYNTAX UInteger32
--  Units
--    tenths of seconds
    ACCESS read-write
    STATUS mandatory
    DESCRIPTION
        "The value of this object, together with that of the
        tn3270eRtCollCtlBucketBndry1 object, defines the range of
        transaction response times counted in the Tn3270eRtDataBucket2
        object:  those greater than the value of the
        tn3270eRtCollCtlBucketBndry1 object, and less than or equal to
        the value of this object."
    DEFVAL { 20 }
    ::= { tn3270eRtCollCtlEntry 9 }

tn3270eRtCollCtlBucketBndry3 OBJECT-TYPE
    SYNTAX UInteger32
--  Units
--    tenths of seconds
    ACCESS read-write
    STATUS mandatory
    DESCRIPTION
        "The value of this object, together with that of the
        tn3270eRtCollCtlBucketBndry2 object, defines the range of
        transaction response times counted in the Tn3270eRtDataBucket3
        object:  those greater than the value of the
        tn3270eRtCollCtlBucketBndry2 object, and less than or equal to
        the value of this object."
    DEFVAL { 50 }
    ::= { tn3270eRtCollCtlEntry 10 }

tn3270eRtCollCtlBucketBndry4 OBJECT-TYPE
    SYNTAX UInteger32
--  Units
--    tenths of seconds
    ACCESS read-write
    STATUS mandatory
    DESCRIPTION
        "The value of this object, together with that of the
        tn3270eRtCollCtlBucketBndry3 object, defines the range of
        transaction response times counted in the Tn3270eRtDataBucket4
        object:  those greater than the value of the
        tn3270eRtCollCtlBucketBndry3 object, and less than or equal to
        the value of this object.
        
        The value of this object also defines the range of transaction
        response times counted in the Tn3270eRtDataBucket5 object:
        those greater than the value of this object."
    DEFVAL { 100 }
    ::= { tn3270eRtCollCtlEntry 11 }

tn3270eRtCollCtlRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows entries to be created and deleted
         in the tn3270eRtCollCtlTable.  An entry in this table
         is deleted by setting this object to destroy(6).
         Deleting an entry in this table has the side-effect
         of removing all entries from the tn3270eRtDataTable
         that are associated with the entry being deleted."
    ::= { tn3270eRtCollCtlEntry 12 }

tn3270eRtDataTable OBJECT-TYPE
    SYNTAX SEQUENCE OF Tn3270eRtDataEntry
    ACCESS not-accessible
    STATUS mandatory
    DESCRIPTION
        "The response time data table. Entries in this table are
         created based on entries in the tn3270eRtCollCtlTable."
    ::= { tn3270eRtObjects 2 }

tn3270eRtDataEntry OBJECT-TYPE
    SYNTAX Tn3270eRtDataEntry
    ACCESS not-accessible
    STATUS mandatory
    DESCRIPTION
        "Entries in this table are created based upon the
        tn3270eRtCollCtlTable.  When the corresponding
        tn3270eRtCollCtlType has aggregate(0) specified, a single
        entry is created in this table, with a tn3270eRtDataClientAddrType
        of unknown(0), a zero-length octet string value for
        tn3270eRtDataClientAddress, and a tn3270eRtDataClientPort value of
        0.  When aggregate(0) is not specified, a separate entry is
        created for each client in the group.
        
        Note that the following objects defined within an
        entry in this table can wrap:
           tn3270eRtDataTotalRt
           tn3270eRtDataTotalIpRt
           tn3270eRtDataTransCount
           tn3270eRtDataDrCount
           tn3270eRtDataElapsRnTrpSq
           tn3270eRtDataElapsIpRtSq
           tn3270eRtDataBucket1
           tn3270eRtDataBucket2
           tn3270eRtDataBucket3
           tn3270eRtDataBucket4
           tn3270eRtDataBucket5"
    INDEX { tn3270eSrvrConfIndex, tn3270eRtCollCtlClientGroupName, tn3270eRtDataClientAddrType, tn3270eRtDataClientAddress, tn3270eRtDataClientPort }
    ::= { tn3270eRtDataTable 1 }

Tn3270eRtDataEntry ::= SEQUENCE {
    tn3270eRtDataClientAddrType Tn3270eAddrType,
    tn3270eRtDataClientAddress Tn3270eTAddress,
    tn3270eRtDataClientPort UInteger32,
    tn3270eRtDataAvgRt Gauge32,
    tn3270eRtDataAvgIpRt Gauge32,
    tn3270eRtDataAvgTransCount Counter32,
    tn3270eRtDataIntTimeStamp DateAndTime,
    tn3270eRtDataTotalRt Counter32,
    tn3270eRtDataTotalIpRt Counter32,
    tn3270eRtDataTransCount Counter32,
    tn3270eRtDataDrCount Counter32,
    tn3270eRtDataElapsRndTrpSq UInteger32,
    tn3270eRtDataElapsIpRtSq UInteger32,
    tn3270eRtDataBucket1 Counter32,
    tn3270eRtDataBucket2 Counter32,
    tn3270eRtDataBucket3 Counter32,
    tn3270eRtDataBucket4 Counter32,
    tn3270eRtDataBucket5 Counter32,
    tn3270eRtDataRtMethod INTEGER
    }

tn3270eRtDataClientAddrType OBJECT-TYPE
    SYNTAX Tn3270eAddrType
--    Rsyntax INTEGER {
--        unknown(0),
--        ipv4(1),
--        ipv6(2)
--        }
    ACCESS not-accessible
    STATUS mandatory
    DESCRIPTION
        "Indicates the type of address that following in the
         instance OID represented by tn3270eRtDataClientAddress."
    ::= { tn3270eRtDataEntry 1 }

tn3270eRtDataClientAddress OBJECT-TYPE
    SYNTAX Tn3270eTAddress
--    Rsyntax OCTET STRING(SIZE(0..255))
    ACCESS not-accessible
    STATUS mandatory
    DESCRIPTION
        "Contains the IP address of the TN3270 client being
         monitored. A null octet string is used if the aggregate
         of the Client Group is being collected "
    ::= { tn3270eRtDataEntry 2 }

tn3270eRtDataClientPort OBJECT-TYPE
    SYNTAX UInteger32(0..65535)
    ACCESS not-accessible
    STATUS mandatory
    DESCRIPTION
        "Contains the client port number of the TN3270 client being
         monitored.  The value 0 is used if aggregate data is being
         collected for the client group, or if the
         tn3270eRtDataClientAddrType identifies an address type that
         does not support ports."
    ::= { tn3270eRtDataEntry 3 }

tn3270eRtDataAvgRt OBJECT-TYPE
    SYNTAX Gauge32
--  Units
--    tenths of seconds
    ACCESS read-only
    STATUS mandatory
    DESCRIPTION
        "The average total response time measured over the last
         collection interval."
    DEFVAL { 0 }
    ::= { tn3270eRtDataEntry 4 }

tn3270eRtDataAvgIpRt OBJECT-TYPE
    SYNTAX Gauge32
--  Units
--    tenths of seconds
    ACCESS read-only
    STATUS mandatory
    DESCRIPTION
        "The average IP response time measured over the last
         collection interval."
    DEFVAL { 0 }
    ::= { tn3270eRtDataEntry 5 }

tn3270eRtDataAvgTransCount OBJECT-TYPE
    SYNTAX Counter32
--  Units
--    transactions
    ACCESS read-only
    STATUS mandatory
    DESCRIPTION
        "The sliding transaction count used for calculating the values
         of the tn3270eRtDataAvgRt and tn3270eRtDataAvgIpRt objects.
         The actual transaction count is available in the
         tn3270eRtDataTransCount object."
    ::= { tn3270eRtDataEntry 6 }

tn3270eRtDataIntTimeStamp OBJECT-TYPE
    SYNTAX DateAndTime
--    Rsyntax OCTET STRING(SIZE(8 | 11))
    ACCESS read-only
    STATUS mandatory
    DESCRIPTION
        "The date and time of the last interval that tn3270eRtDataAvgRt,
         tn3270eRtDataAvgIpRt, and tn3270eRtDataAvgTransCount were
         calculated."
    ::= { tn3270eRtDataEntry 7 }

tn3270eRtDataTotalRt OBJECT-TYPE
    SYNTAX Counter32
--  Units
--    tenths of seconds
    ACCESS read-only
    STATUS mandatory
    DESCRIPTION
        "A count of the total response time collected."
    ::= { tn3270eRtDataEntry 8 }

tn3270eRtDataTotalIpRt OBJECT-TYPE
    SYNTAX Counter32
--  Units
--    tenths of seconds
    ACCESS read-only
    STATUS mandatory
    DESCRIPTION
        "A count of the total IP-network response time collected."
    ::= { tn3270eRtDataEntry 9 }

tn3270eRtDataTransCount OBJECT-TYPE
    SYNTAX Counter32
--  Units
--    transactions
    ACCESS read-only
    STATUS mandatory
    DESCRIPTION
        "A count of the total number of transactions detected."
    ::= { tn3270eRtDataEntry 10 }

tn3270eRtDataDrCount OBJECT-TYPE
    SYNTAX Counter32
--  Units
--    transactions
    ACCESS read-only
    STATUS mandatory
    DESCRIPTION
        "A count of the total number of definite responses detected."
    ::= { tn3270eRtDataEntry 11 }

tn3270eRtDataElapsRndTrpSq OBJECT-TYPE
    SYNTAX UInteger32
--  Units
--    tenths of seconds squared
    ACCESS read-only
    STATUS mandatory
    DESCRIPTION
        "The sum of the elapsed round trip time squared.  A sum of the
         squares is keep in order to calculate a variance."
    DEFVAL { 0 }
    ::= { tn3270eRtDataEntry 12 }

tn3270eRtDataElapsIpRtSq OBJECT-TYPE
    SYNTAX UInteger32
--  Units
--    tenths of seconds squared
    ACCESS read-only
    STATUS mandatory
    DESCRIPTION
        "The sum of the elapsed IP round trip time squared.  A sum of
         the squares is keep in order to calculate a variance."
    DEFVAL { 0 }
    ::= { tn3270eRtDataEntry 13 }

tn3270eRtDataBucket1 OBJECT-TYPE
    SYNTAX Counter32
    ACCESS read-only
    STATUS mandatory
    DESCRIPTION
        "A count of the response times falling into bucket 1."
    ::= { tn3270eRtDataEntry 14 }

tn3270eRtDataBucket2 OBJECT-TYPE
    SYNTAX Counter32
    ACCESS read-only
    STATUS mandatory
    DESCRIPTION
        "A count of the response times falling into bucket 2."
    ::= { tn3270eRtDataEntry 15 }

tn3270eRtDataBucket3 OBJECT-TYPE
    SYNTAX Counter32
    ACCESS read-only
    STATUS mandatory
    DESCRIPTION
        "A count of the response times falling into bucket 3."
    ::= { tn3270eRtDataEntry 16 }

tn3270eRtDataBucket4 OBJECT-TYPE
    SYNTAX Counter32
    ACCESS read-only
    STATUS mandatory
    DESCRIPTION
        "A count of the response times falling into bucket 4."
    ::= { tn3270eRtDataEntry 17 }

tn3270eRtDataBucket5 OBJECT-TYPE
    SYNTAX Counter32
    ACCESS read-only
    STATUS mandatory
    DESCRIPTION
        "A count of the response times falling into bucket 5."
    ::= { tn3270eRtDataEntry 18 }

tn3270eRtDataRtMethod OBJECT-TYPE
    SYNTAX INTEGER {
        none(0),
        responses(1),
        timemark(2)
        }
    ACCESS read-only
    STATUS mandatory
    DESCRIPTION
        "The value of this object indicates the method that was used
         in calculating the IP Network Time."
    ::= { tn3270eRtDataEntry 19 }

tn3270eRtExceeded TRAP-TYPE
-- Reverse mappable trap
    ENTERPRISE tn3270eRtMIB
    VARIABLES {
        tn3270eSrvrConfIndex, tn3270eRtCollCtlClientGroupName, 
        tn3270eRtDataClientAddrType, tn3270eRtDataClientAddress, 
        tn3270eRtDataIntTimeStamp, tn3270eRtDataAvgRt, 
        tn3270eRtDataAvgIpRt, tn3270eRtDataAvgTransCount, 
        tn3270eRtDataRtMethod }
--  Status
--    mandatory
    DESCRIPTION
        "This notification is generated when the average response time,
        tn3270eRtDataAvgRt, exceeds tn3270eRtCollCtlThresholdHigh at
        the end of a collection interval specified by
        tn3270eCollCtlSPeriod times tn3270eCollCtlSPMult.  Note that
        the corresponding tn3270eCollCtlType must have traps(5) and
        average(3) set for this notification to be generated.  In
        addition, tn3270eRtDataAvgTransCount,
        tn3270eRtCollCtlThreshHigh and tn3270eRtDataAvgRt are
        algorithmically compared to tn3270eRtCollCtlIdleRate for
        determination if this will be suppressed."
    ::= 1

tn3270eRtOkay TRAP-TYPE
-- Reverse mappable trap
    ENTERPRISE tn3270eRtMIB
    VARIABLES {
        tn3270eSrvrConfIndex, tn3270eRtCollCtlClientGroupName, 
        tn3270eRtDataClientAddrType, tn3270eRtDataClientAddress, 
        tn3270eRtDataIntTimeStamp, tn3270eRtDataAvgRt, 
        tn3270eRtDataAvgIpRt, tn3270eRtDataAvgTransCount, 
        tn3270eRtDataRtMethod }
--  Status
--    mandatory
    DESCRIPTION
        "This notification is generated when the average response time,
        tn3270eRtDataAvgRt, falls below tn3270eRtCollCtlThresholdLow at
        the end of a collection interval specified by
        tn3270eCollCtlSPeriod times tn3270eCollCtlSPMult, after a
        tn3270eRtExceeded notification was generated.  Note that the
        corresponding tn3270eCollCtlType must have traps(5) and
        average(3) set for this notification to be generated."
    ::= 2

tn3270eRtCollStart TRAP-TYPE
-- Reverse mappable trap
    ENTERPRISE tn3270eRtMIB
    VARIABLES {
        tn3270eSrvrConfIndex, tn3270eRtCollCtlClientGroupName, 
        tn3270eRtDataClientAddrType, tn3270eRtDataClientAddress, 
        tn3270eResMapElementName, tn3270eResMapElementType }
--  Status
--    mandatory
    DESCRIPTION
        "This notification is generated when response time data
        collection is enabled for a member of a client group.  In order
        for this notification to occur the corresponding
        tn3270eRtCollCtlType must have traps(5) selected.  The objects
        tn3270eResMapElementName and tn3270eResMapElementType contains
        valid values only if tn3270eRtDataClientAddress contains a
        valid IP address (rather than the null octet string)."
    ::= 3

tn3270eRtCollEnd TRAP-TYPE
-- Reverse mappable trap
    ENTERPRISE tn3270eRtMIB
    VARIABLES {
        tn3270eSrvrConfIndex, tn3270eRtCollCtlClientGroupName, 
        tn3270eRtDataClientAddrType, tn3270eRtDataClientAddress, 
        tn3270eRtDataClientPort, tn3270eRtDataAvgRt, 
        tn3270eRtDataAvgIpRt, tn3270eRtDataAvgTransCount, 
        tn3270eRtDataIntTimeStamp, tn3270eRtDataTotalRt, 
        tn3270eRtDataTotalIpRt, tn3270eRtDataTransCount, 
        tn3270eRtDataDrCount, tn3270eRtDataElapsRndTrpSq, 
        tn3270eRtDataElapsIpRtSq, tn3270eRtDataBucket1, 
        tn3270eRtDataBucket2, tn3270eRtDataBucket3, 
        tn3270eRtDataBucket4, tn3270eRtDataBucket5, 
        tn3270eRtDataRtMethod }
--  Status
--    mandatory
    DESCRIPTION
        "This notification is generated when a tn3270eRtDataEntry is
        deleted after being active (actual data collected), in order to
        enable a management application monitoring a tn3270eRtDataTable
        entry to end get the entry's final values.  Note that the
        corresponding tn3270eCollCtlType must have traps(5) set for this
        notification to be generated."
    ::= 4

tn3270eRtGroup OBJECT IDENTIFIER ::= { tn3270eRtGroups 1 }
-- OBJECT-GROUP
--  Status
--    mandatory
--  Descr
--    This group is mandatory for all host supporting the
--     TN3270E-RT-MIB. 
--  objects
--    tn3270eRtCollCtlType, tn3270eRtCollCtlSPeriod, 
--    tn3270eRtCollCtlSPMult, tn3270eRtCollCtlThreshHigh, 
--    tn3270eRtCollCtlThreshLow, tn3270eRtCollCtlIdleRate, 
--    tn3270eRtCollCtlBucketBndry1, tn3270eRtCollCtlBucketBndry2, 
--    tn3270eRtCollCtlBucketBndry3, tn3270eRtCollCtlBucketBndry4, 
--    tn3270eRtCollCtlRowStatus, tn3270eRtDataClientPort, 
--    tn3270eRtDataAvgRt, tn3270eRtDataAvgIpRt, 
--    tn3270eRtDataAvgTransCount, tn3270eRtDataIntTimeStamp, 
--    tn3270eRtDataTotalRt, tn3270eRtDataTotalIpRt, 
--    tn3270eRtDataTransCount, tn3270eRtDataDrCount, 
--    tn3270eRtDataElapsRndTrpSq, tn3270eRtDataElapsIpRtSq, 
--    tn3270eRtDataBucket1, tn3270eRtDataBucket2, 
--    tn3270eRtDataBucket3, tn3270eRtDataBucket4, 
--    tn3270eRtDataBucket5, tn3270eRtDataRtMethod

tn3270eRtCompliance OBJECT IDENTIFIER ::= { tn3270eRtCompliances 1 }
-- MODULE-COMPLIANCE
--  Status
--    mandatory
--  Descr
--    The compliance statement for agents that support the
--     TN327E-RT-MIB 
--  Module
--    >>current<<
--   MandGroup
--    tn3270eRtGroup
--   ObjVar
--    tn3270eRtCollCtlSPeriod


END
