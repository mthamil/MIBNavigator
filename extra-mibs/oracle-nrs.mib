/*
   $Header: nrs.v1 15-jul-96.17:18:49 cluo Exp $
   $Log:  $
# Revision 1.1  1995/05/26  22:14:28  dlau
# Initial revision
#
*/

#include "ode/objids.smi"
#include "ode/types.smi"
#include "netserv.smi"


ORAINTERCHANGE-MIB DEFINITIONS ::= BEGIN


IMPORTS
	TRAP-TYPE
		FROM RFC-1215
	DisplayString
		FROM RFC1213-MIB
	OBJECT-TYPE
		FROM RFC-1212
	Counter, Gauge, enterprises
		FROM RFC1155-SMI
	TimeStamp, applIndex
		FROM APPLICATION-MIB;

oracle OBJECT IDENTIFIER ::= { enterprises 111 }

oraInterchangeMIB OBJECT IDENTIFIER ::= { oracle  7 }

oraInterchangeObjects OBJECT IDENTIFIER ::= { oraInterchangeMIB  1 }

oraInterchgTable OBJECT-TYPE
    SYNTAX  SEQUENCE OF OraInterchgEntry
    ACCESS  not-accessible
    STATUS  mandatory
    DESCRIPTION
           "The table of information about a Multiprotocol Interchange."
    ::= { oraInterchangeObjects  1 }

oraInterchgEntry OBJECT-TYPE
    SYNTAX  OraInterchgEntry
    ACCESS  not-accessible
    STATUS  mandatory
    DESCRIPTION
           "An entry in the table associated with a Multiprotocol Interchange."
    INDEX   { applIndex }
           C_NEXT_FUNC next_oraInterchgEntry
    ::= { oraInterchgTable  1 }

OraInterchgEntry ::=
    SEQUENCE {
        oraInterchgConfigDirectory
            DisplayString,

        oraInterchgContactInfo
            DisplayString
    }

oraInterchgConfigDirectory OBJECT-TYPE
    SYNTAX  DisplayString
    ACCESS  read-only
    STATUS  mandatory
    DESCRIPTION
           "The directory which contains the Multiprotocol Interchange 
	   configuration files.  The default TNS_ADMIN directory is 
	   /$ORACLE_HOME/NETWORK/ADMIN."
    ::= { oraInterchgEntry  1 }

oraInterchgContactInfo OBJECT-TYPE
    SYNTAX  DisplayString
    ACCESS  read-only
    STATUS  mandatory
    DESCRIPTION
           "Provides the information of the person to contact for the  
	   Multiprotocol Interchange issue, this information is read 
	   from the SNMP.ORA file."
    ::= { oraInterchgEntry  2 }

oraNavigatorTable OBJECT-TYPE
    SYNTAX  SEQUENCE OF OraNavigatorEntry
    ACCESS  not-accessible
    STATUS  mandatory
    DESCRIPTION
           "The table of information about the status of a Navigator."
    ::= { oraInterchangeObjects  2 }

oraNavigatorEntry OBJECT-TYPE
    SYNTAX  OraNavigatorEntry
    ACCESS  not-accessible
    STATUS  mandatory
    DESCRIPTION
           "An entry in the table associated with a Navigator."
    INDEX   { applIndex }
            C_NEXT_FUNC next_oraNavigatorEntry
    ::= { oraNavigatorTable  1 }

OraNavigatorEntry ::=
    SEQUENCE {
        oraNavigatorRunningTime
            DisplayString,

        oraNavigatorLogging
            INTEGER,

        oraNavigatorLoggingLevel
            INTEGER,

        oraNavigatorLogFile
            DisplayString,

        oraNavigatorTraceLevel
            INTEGER,

        oraNavigatorTraceFile
            DisplayString,

        oraNavigatorStoppable
            INTEGER,

        oraNavigatorAccumulatedSuccessfulRequests
            Counter,

        oraNavigatorAccumulatedFailedRequests
            Counter,

        oraNavigatorState
            INTEGER,

        oraNavigatorErrors
            DisplayString,

        oraNavigatorErrorMessage
            DisplayString
    }

oraNavigatorRunningTime OBJECT-TYPE
    SYNTAX  DisplayString
    ACCESS  read-only
    STATUS  mandatory
    DESCRIPTION
           "The elapsed time in secs since a Navigator was last started."
    ::= { oraNavigatorEntry  1 }

oraNavigatorLogging OBJECT-TYPE
    SYNTAX  INTEGER {
    on(1),
    off(2)
}
    ACCESS  read-write
    STATUS  mandatory
    DESCRIPTION
           "Indicates whether a Navigator should log the requests."
    ::= { oraNavigatorEntry  2 }

oraNavigatorLoggingLevel OBJECT-TYPE
    SYNTAX  INTEGER {
    all(1),
    errors(2)
}
    ACCESS  read-write
    STATUS  mandatory
    DESCRIPTION
           "Indicates whether a Navigator should log all the requests or 
	   errors only."
    ::= { oraNavigatorEntry  3 }

oraNavigatorLogFile OBJECT-TYPE
    SYNTAX  DisplayString
    ACCESS  read-only
    STATUS  mandatory
    DESCRIPTION
           "Indicates the name of the log file the Navigator created.
	   Default log file name is /$ORACLE_HOME/network/log/navgatr.log,
	   where $ORACLE_HOME is the path which the ORACLE_HOME points to."
    ::= { oraNavigatorEntry  4 }

oraNavigatorTraceLevel OBJECT-TYPE
    SYNTAX  INTEGER {
    level1(1),
    level2(2),
    level3(3),
    user(4),
    level5(5),
    admin(6),
    level7(7),
    level8(8),
    level9(9),
    level10(10),
    level11(11),
    level12(12),
    level13(13),
    level14(14),
    level15(15),
    level16(16),
    off(17)
}
    ACCESS  read-write
    STATUS  mandatory
    DESCRIPTION
           "Indicates the level at which a Navigator should be traced."
    ::= { oraNavigatorEntry  5 }

oraNavigatorTraceFile OBJECT-TYPE
    SYNTAX  DisplayString
    ACCESS  read-only
    STATUS  mandatory
    DESCRIPTION
           "Indicates the name of the trace file the Navigator created.
	   On an Unix platform, the default trace file name is 
	   /$ORACLE_HOME/network/trace/nav_pid.trc, where pid is the process
	   ID of the Navigator and $ORACLE_HOME is the path which the 
	   ORACLE_HOME points to."
    ::= { oraNavigatorEntry  6 }

oraNavigatorStoppable OBJECT-TYPE
    SYNTAX  INTEGER {
    yes(1),
    no(2)
}
    ACCESS  read-write
    STATUS  mandatory
    DESCRIPTION
           "Indicates whether a Navigator can be stopped using the  
	   Multiprotocol Interchange Control Utility program."
    ::= { oraNavigatorEntry  7 }

oraNavigatorAccumulatedSuccessfulRequests OBJECT-TYPE
    SYNTAX  Counter
    ACCESS  read-only
    STATUS  mandatory
    DESCRIPTION
           "The total number of successful requests received by a Navigator."
    ::= { oraNavigatorEntry  8 }

oraNavigatorAccumulatedFailedRequests OBJECT-TYPE
    SYNTAX  Counter
    ACCESS  read-only
    STATUS  mandatory
    DESCRIPTION
           "The total number of unsuccessful requests received by a Navigator."
    ::= { oraNavigatorEntry  9 }

oraNavigatorState OBJECT-TYPE
    SYNTAX  INTEGER {
    up(1),
    down(2)
}
    ACCESS  read-only
    STATUS  mandatory
    DESCRIPTION
           "Indicates the current state of a Navigator."
    ::= { oraNavigatorEntry  10 }

oraNavigatorErrors OBJECT-TYPE
    SYNTAX  DisplayString
    ACCESS  read-only
    STATUS  mandatory
    DESCRIPTION
           "The error stack of a Navigator when it fails."
    ::= { oraNavigatorEntry  11 }

oraNavigatorErrorMessage OBJECT-TYPE
    SYNTAX  DisplayString
    ACCESS  read-only
    STATUS  mandatory
    DESCRIPTION
           "The error message of a Navigator when it fails."
    ::= { oraNavigatorEntry  12 }

oraNavigatorListenAddressTable OBJECT-TYPE
    SYNTAX  SEQUENCE OF OraNavigatorListenAddressEntry
    ACCESS  not-accessible
    STATUS  mandatory
    DESCRIPTION
           "The table of information about the addresses that a Navigator 
	   is listening on."
    ::= { oraInterchangeObjects  3 }

oraNavigatorListenAddressEntry OBJECT-TYPE
    SYNTAX  OraNavigatorListenAddressEntry
    ACCESS  not-accessible
    STATUS  mandatory
    DESCRIPTION
           "An entry in the table associated with the addresses at which 
	   a Navigator is listening on."
    INDEX   { applIndex,  oraNavigatorListenAddressIndex }
            C_NEXT_FUNC next_oraNavigatorListenAddressEntry
    ::= { oraNavigatorListenAddressTable  1 }

OraNavigatorListenAddressEntry ::=
    SEQUENCE {
        oraNavigatorListenAddressIndex
            INTEGER,

        oraNavigatorListenAddress
            DisplayString
    }

oraNavigatorListenAddressIndex OBJECT-TYPE
    SYNTAX  INTEGER
    ACCESS  read-only
    STATUS  mandatory
    DESCRIPTION
           "A numeric index, unique among all the listen addresses
	  at which a Navigator is listening on."
    ::= { oraNavigatorListenAddressEntry  1 }

oraNavigatorListenAddress OBJECT-TYPE
    SYNTAX  DisplayString
    ACCESS  read-only
    STATUS  mandatory
    DESCRIPTION
           "The addresses at which a Navigator is listening on."
    ::= { oraNavigatorListenAddressEntry  2 }

oraNavigatorFailedAddressTable OBJECT-TYPE
    SYNTAX  SEQUENCE OF OraNavigatorFailedAddressEntry
    ACCESS  not-accessible
    STATUS  mandatory
    DESCRIPTION
           "The table of information about the addresses that a Navigator 
	   fails to listen on."
    ::= { oraInterchangeObjects  4 }

oraNavigatorFailedAddressEntry OBJECT-TYPE
    SYNTAX  OraNavigatorFailedAddressEntry
    ACCESS  not-accessible
    STATUS  mandatory
    DESCRIPTION
           "An entry in the table associated with the addresses  
	   that a Navigator fails to listen on."
    INDEX   { applIndex,  oraNavigatorFailedAddressIndex }
            C_NEXT_FUNC next_oraNavigatorFailedAddressEntry
    ::= { oraNavigatorFailedAddressTable  1 }

OraNavigatorFailedAddressEntry ::=
    SEQUENCE {
        oraNavigatorFailedAddressIndex
            INTEGER,

        oraNavigatorFailedAddress
            DisplayString
    }

oraNavigatorFailedAddressIndex OBJECT-TYPE
    SYNTAX  INTEGER
    ACCESS  read-only
    STATUS  mandatory
    DESCRIPTION
           "A numeric index, unique among all the addresses which 
	  a Navigator fails to listen on."
    ::= { oraNavigatorFailedAddressEntry  1 }

oraNavigatorFailedAddress OBJECT-TYPE
    SYNTAX  DisplayString
    ACCESS  read-only
    STATUS  mandatory
    DESCRIPTION
           "The address that a Navigator fails to listen on."
    ::= { oraNavigatorFailedAddressEntry  2 }

oraNavigatorRouteAddressTable OBJECT-TYPE
    SYNTAX  SEQUENCE OF OraNavigatorRouteAddressEntry
    ACCESS  not-accessible
    STATUS  mandatory
    DESCRIPTION
           "The table of information about the routable addresses that a  
	   Navigator has."
    ::= { oraInterchangeObjects  5 }

oraNavigatorRouteAddressEntry OBJECT-TYPE
    SYNTAX  OraNavigatorRouteAddressEntry
    ACCESS  not-accessible
    STATUS  mandatory
    DESCRIPTION
           "An entry in the table associated with the routable addresses  
	   that a Navigator has."
    INDEX   { applIndex,  oraNavigatorRouteAddressIndex }
            C_NEXT_FUNC next_oraNavigatorRouteAddressEntry
    ::= { oraNavigatorRouteAddressTable  1 }

OraNavigatorRouteAddressEntry ::=
    SEQUENCE {
        oraNavigatorRouteAddressIndex
            INTEGER,

        oraNavigatorRouteAddress
            DisplayString
    }

oraNavigatorRouteAddressIndex OBJECT-TYPE
    SYNTAX  INTEGER
    ACCESS  read-only
    STATUS  mandatory
    DESCRIPTION
           "A numeric index, unique among all the routable addresses
	  that a Navigator has."
    ::= { oraNavigatorRouteAddressEntry  1 }

oraNavigatorRouteAddress OBJECT-TYPE
    SYNTAX  DisplayString
    ACCESS  read-only
    STATUS  mandatory
    DESCRIPTION
           "The routable address that a Navigator has."
    ::= { oraNavigatorRouteAddressEntry  2 }

oraCmanagerTable OBJECT-TYPE
    SYNTAX  SEQUENCE OF OraCmanagerEntry
    ACCESS  not-accessible
    STATUS  mandatory
    DESCRIPTION
           "The table of information about the status of a Connection
	   Manager."
    ::= { oraInterchangeObjects  6 }

oraCmanagerEntry OBJECT-TYPE
    SYNTAX  OraCmanagerEntry
    ACCESS  not-accessible
    STATUS  mandatory
    DESCRIPTION
           "An entry in the table associated with a Connection Manager."
    INDEX   { applIndex }
            C_NEXT_FUNC next_oraCmanagerEntry
    ::= { oraCmanagerTable  1 }

OraCmanagerEntry ::=
    SEQUENCE {
        oraCmanagerStartTime
            DisplayString,

        oraCmanagerRunningTime
            DisplayString,

        oraCmanagerLogging
            INTEGER,

        oraCmanagerLogFile
            DisplayString,

        oraCmanagerTraceLevel
            INTEGER,

        oraCmanagerTraceFile
            DisplayString,

        oraCmanagerStoppable
            INTEGER,

        oraCmanagerMaximumPumps
            INTEGER,

        oraCmanagerMaximumConnectionsPerPump
            INTEGER,

        oraCmanagerPumpStrategy
            INTEGER,

        oraCmanagerActivePumps
            Gauge,

        oraCmanagerMaximumConnections
            INTEGER,

        oraCmanagerCurrentConnectionsInUse
            Gauge,

        oraCmanagerAccumulatedSuccessfulConnections
            Counter,

        oraCmanagerAccumulatedFailedConnections
            Counter,

        oraCmanagerImmediateAverageBytes
            INTEGER,

        oraCmanagerMaximumConnectTime
            INTEGER,

        oraCmanagerMinimumConnectTime
            INTEGER,

        oraCmanagerAverageConnectTime
            INTEGER,

        oraCmanagerMaximumConnectDuration
            INTEGER,

        oraCmanagerState
            INTEGER,

        oraCmanagerErrors
            DisplayString,

        oraCmanagerErrorMessage
            DisplayString
    }

oraCmanagerStartTime OBJECT-TYPE
    SYNTAX  DisplayString
    ACCESS  read-only
    STATUS  mandatory
    DESCRIPTION
           "The time when a Connection Manager was started.  The format is 
	  date-month-yr hr:min:sec."
    ::= { oraCmanagerEntry  1 }

oraCmanagerRunningTime OBJECT-TYPE
    SYNTAX  DisplayString
    ACCESS  read-only
    STATUS  mandatory
    DESCRIPTION
           "The elapsed time in secs since a Connection Manager 
           was last started."
    ::= { oraCmanagerEntry  2 }

oraCmanagerLogging OBJECT-TYPE
    SYNTAX  INTEGER {
    on(1),
    off(2)
}
    ACCESS  read-write
    STATUS  mandatory
    DESCRIPTION
           "Indicates whether a Connection Manager should log the requests."
    ::= { oraCmanagerEntry  3 }

oraCmanagerLogFile OBJECT-TYPE
    SYNTAX  DisplayString
    ACCESS  read-only
    STATUS  mandatory
    DESCRIPTION
           "Indicates the name of the log file the Connection Manager created. 
	   The default log file name is /$ORACLE_HOME/network/log/intlsnr.log,
           where $ORACLE_HOME is the path which the ORACLE_HOME points to."
    ::= { oraCmanagerEntry  4 }

oraCmanagerTraceLevel OBJECT-TYPE
    SYNTAX  INTEGER {
    level1(1),
    level2(2),
    level3(3),
    user(4),
    level5(5),
    admin(6),
    level7(7),
    level8(8),
    level9(9),
    level10(10),
    level11(11),
    level12(12),
    level13(13),
    level14(14),
    level15(15),
    level16(16),
    off(17)
}
    ACCESS  read-write
    STATUS  mandatory
    DESCRIPTION
           "Indicates the level at which a Connection Manager should be traced."
    ::= { oraCmanagerEntry  5 }

oraCmanagerTraceFile OBJECT-TYPE
    SYNTAX  DisplayString
    ACCESS  read-only
    STATUS  mandatory
    DESCRIPTION
           "Indicates the name of the trace file the Connection Manager created.
	   On an Unix platform, the default trace file name is 
	   /$ORACLE_HOME/network/trace/cmg_pid.trc, where pid is the process
	   ID of the Connection Manager and $ORACLE_HOME is the path which
	   ORACLE_HOME points to."
    ::= { oraCmanagerEntry  6 }

oraCmanagerStoppable OBJECT-TYPE
    SYNTAX  INTEGER {
    yes(1),
    no(2)
}
    ACCESS  read-write
    STATUS  mandatory
    DESCRIPTION
           "Indicates whether a Connection Manager can be stopped
	   by the Multiprotocol Interchange Control Utility program."
    ::= { oraCmanagerEntry  7 }

oraCmanagerMaximumPumps OBJECT-TYPE
    SYNTAX  INTEGER
    ACCESS  read-write
    STATUS  mandatory
    DESCRIPTION
           "The maximum number of pumps that can be started by the Connection
	  Manager."
    ::= { oraCmanagerEntry  8 }

oraCmanagerMaximumConnectionsPerPump OBJECT-TYPE
    SYNTAX  INTEGER
    ACCESS  read-write
    STATUS  mandatory
    DESCRIPTION
           "The maximum number of connections per pump that can be started by
	   the Connection Manager."
    ::= { oraCmanagerEntry  9 }

oraCmanagerPumpStrategy OBJECT-TYPE
    SYNTAX  INTEGER {
    distribute(1),
    group(2)
}
    ACCESS  read-write
    STATUS  mandatory
    DESCRIPTION
           "Indicates a Pump allocation strategy."
    ::= { oraCmanagerEntry  10 }

oraCmanagerActivePumps OBJECT-TYPE
    SYNTAX  Gauge
    ACCESS  read-only
    STATUS  mandatory
    DESCRIPTION
           "The total number of pumps that are currently active."
    ::= { oraCmanagerEntry  11 }

oraCmanagerMaximumConnections OBJECT-TYPE
    SYNTAX  INTEGER
    ACCESS  read-only
    STATUS  mandatory
    DESCRIPTION
           "The maximum number of connections that are available."
    ::= { oraCmanagerEntry  12 }

oraCmanagerCurrentConnectionsInUse OBJECT-TYPE
    SYNTAX  Gauge
    ACCESS  read-only
    STATUS  mandatory
    DESCRIPTION
           "The total number of connections that are currently used."
    ::= { oraCmanagerEntry  13 }

oraCmanagerAccumulatedSuccessfulConnections OBJECT-TYPE
    SYNTAX  Counter
    ACCESS  read-only
    STATUS  mandatory
    DESCRIPTION
           "The total number of successful connections through the 
	  Multiprotocol Interchange."
    ::= { oraCmanagerEntry  14 }

oraCmanagerAccumulatedFailedConnections OBJECT-TYPE
    SYNTAX  Counter
    ACCESS  read-only
    STATUS  mandatory
    DESCRIPTION
           "The total number of unsuccessful connections through the
	  Multiprotocol Interchange."
    ::= { oraCmanagerEntry  15 }

oraCmanagerImmediateAverageBytes OBJECT-TYPE
    SYNTAX  INTEGER
    ACCESS  read-only
    STATUS  mandatory
    DESCRIPTION
           "The immediate average number of bytes sent per second."
    ::= { oraCmanagerEntry  16 }

oraCmanagerMaximumConnectTime OBJECT-TYPE
    SYNTAX  INTEGER
    ACCESS  read-only
    STATUS  mandatory
    DESCRIPTION
           "The maximum time in centi-seconds to establish a connection."
    ::= { oraCmanagerEntry  17 }

oraCmanagerMinimumConnectTime OBJECT-TYPE
    SYNTAX  INTEGER
    ACCESS  read-only
    STATUS  mandatory
    DESCRIPTION
           "The minimum time in centi-seconds to establish a connection."
    ::= { oraCmanagerEntry  18 }

oraCmanagerAverageConnectTime OBJECT-TYPE
    SYNTAX  INTEGER
    ACCESS  read-only
    STATUS  mandatory
    DESCRIPTION
           "The average time in centi-seconds to establish a connection."
    ::= { oraCmanagerEntry  19 }

oraCmanagerMaximumConnectDuration OBJECT-TYPE
    SYNTAX  INTEGER
    ACCESS  read-only
    STATUS  mandatory
    DESCRIPTION
           "The maximum connection duration time in centi-seconds.  This is the 
	  elapsed time between a connection is established and before the
	  connection is terminated."
    ::= { oraCmanagerEntry  20 }

oraCmanagerState OBJECT-TYPE
    SYNTAX  INTEGER {
    up(1),
    down(2)
}
    ACCESS  read-only
    STATUS  mandatory
    DESCRIPTION
           "Indicates the current state of a Connection Manager."
    ::= { oraCmanagerEntry  21 }

oraCmanagerErrors OBJECT-TYPE
    SYNTAX  DisplayString
    ACCESS  read-only
    STATUS  mandatory
    DESCRIPTION
           "The error stack of a Connection Manager when it fails."
    ::= { oraCmanagerEntry  22 }

oraCmanagerErrorMessage OBJECT-TYPE
    SYNTAX  DisplayString
    ACCESS  read-only
    STATUS  mandatory
    DESCRIPTION
           "The error message of a Connection Manager when it fails."
    ::= { oraCmanagerEntry  23 }

oraCmanagerListenAddressTable OBJECT-TYPE
    SYNTAX  SEQUENCE OF OraCmanagerListenAddressEntry
    ACCESS  not-accessible
    STATUS  mandatory
    DESCRIPTION
           "The table of information about the addresses that a  
	   Connection Manager is listening on."
    ::= { oraInterchangeObjects  7 }

oraCmanagerListenAddressEntry OBJECT-TYPE
    SYNTAX  OraCmanagerListenAddressEntry
    ACCESS  not-accessible
    STATUS  mandatory
    DESCRIPTION
           "An entry in the table associated with the addresses at which 
	   a Connection Manager is listening on."
    INDEX   { applIndex,  oraCmanagerListenAddressIndex }
            C_NEXT_FUNC next_oraCmanagerListenAddressEntry
    ::= { oraCmanagerListenAddressTable  1 }

OraCmanagerListenAddressEntry ::=
    SEQUENCE {
        oraCmanagerListenAddressIndex
            INTEGER,

        oraCmanagerListenAddress
            DisplayString
    }

oraCmanagerListenAddressIndex OBJECT-TYPE
    SYNTAX  INTEGER
    ACCESS  read-only
    STATUS  mandatory
    DESCRIPTION
           "A numeric index, unique among all the listen addresses
	  at which a Connection Manager is listening on."
    ::= { oraCmanagerListenAddressEntry  1 }

oraCmanagerListenAddress OBJECT-TYPE
    SYNTAX  DisplayString
    ACCESS  read-only
    STATUS  mandatory
    DESCRIPTION
           "The address at which a Connection Manager is listening on."
    ::= { oraCmanagerListenAddressEntry  2 }

oraCmanagerFailedAddressTable OBJECT-TYPE
    SYNTAX  SEQUENCE OF OraCmanagerFailedAddressEntry
    ACCESS  not-accessible
    STATUS  mandatory
    DESCRIPTION
           "The table of information about the addresses that a  
	   Connection Manager fails to listen on."
    ::= { oraInterchangeObjects  8 }

oraCmanagerFailedAddressEntry OBJECT-TYPE
    SYNTAX  OraCmanagerFailedAddressEntry
    ACCESS  not-accessible
    STATUS  mandatory
    DESCRIPTION
           "An entry in the table associated with the addresses  
	   that a Connection Manager fails to listen on."
    INDEX   { applIndex,  oraCmanagerFailedAddressIndex }
            C_NEXT_FUNC next_oraCmanagerFailedAddressEntry
    ::= { oraCmanagerFailedAddressTable  1 }

OraCmanagerFailedAddressEntry ::=
    SEQUENCE {
        oraCmanagerFailedAddressIndex
            INTEGER,

        oraCmanagerFailedAddress
            DisplayString
    }

oraCmanagerFailedAddressIndex OBJECT-TYPE
    SYNTAX  INTEGER
    ACCESS  read-only
    STATUS  mandatory
    DESCRIPTION
           "A numeric index, unique among all the addresses which 
	  a Connection Manager fails to listen on."
    ::= { oraCmanagerFailedAddressEntry  1 }

oraCmanagerFailedAddress OBJECT-TYPE
    SYNTAX  DisplayString
    ACCESS  read-only
    STATUS  mandatory
    DESCRIPTION
           "The address that a Connection Manager fails to listen on."
    ::= { oraCmanagerFailedAddressEntry  2 }

oraPumpTable OBJECT-TYPE
    SYNTAX  SEQUENCE OF OraPumpEntry
    ACCESS  not-accessible
    STATUS  mandatory
    DESCRIPTION
           "The table of information about the status of a Pump."
    ::= { oraInterchangeObjects  9 }

oraPumpEntry OBJECT-TYPE
    SYNTAX  OraPumpEntry
    ACCESS  not-accessible
    STATUS  mandatory
    DESCRIPTION
           "An entry in the table associated with a Pump."
    INDEX   { applIndex,  oraPumpIndex }
            C_NEXT_FUNC next_oraPumpEntry
    ::= { oraPumpTable  1 }

OraPumpEntry ::=
    SEQUENCE {
        oraPumpIndex
            INTEGER,

        oraPumpActiveTime
            INTEGER,

        oraPumpTraceLevel
            INTEGER,

        oraPumpTraceFile
            DisplayString,

        oraPumpActiveConnections
            Gauge,

        oraPumpSuccessfulConnections
            Counter,

        oraPumpFailedConnections
            Counter,

        oraPumpAccumulatedBytesSent
            Counter,

        oraPumpCurrentBytesPerSecond
            INTEGER,

        oraPumpMaximumAverageBytes
            INTEGER,

        oraPumpImmediateAverageBytes
            INTEGER,

        oraPumpMaximumConnectTime
            INTEGER,

        oraPumpMinimumConnectTime
            INTEGER,

        oraPumpAverageConnectTime
            INTEGER,

        oraPumpMaximumConnectDuration
            INTEGER,

        oraPumpMaximumBuffers
            INTEGER,

        oraPumpBufferUtilization
            Gauge,

        oraPumpErrors
            DisplayString,

        oraPumpErrorMessage
            DisplayString
    }

oraPumpIndex OBJECT-TYPE
    SYNTAX  INTEGER
    ACCESS  read-only
    STATUS  mandatory
    DESCRIPTION
           "A numeric index, unique among all the pumps."
    ::= { oraPumpEntry  1 }

oraPumpActiveTime OBJECT-TYPE
    SYNTAX  INTEGER
    ACCESS  read-only
    STATUS  mandatory
    DESCRIPTION
           "The number of minutes a Pump remains active after the last
	   connection disconnects."
    ::= { oraPumpEntry  2 }

oraPumpTraceLevel OBJECT-TYPE
    SYNTAX  INTEGER {
    level1(1),
    level2(2),
    level3(3),
    user(4),
    level5(5),
    admin(6),
    level7(7),
    level8(8),
    level9(9),
    level10(10),
    level11(11),
    level12(12),
    level13(13),
    level14(14),
    level15(15),
    level16(16),
    off(17)
}
    ACCESS  read-write
    STATUS  mandatory
    DESCRIPTION
           "Indicates the level at which a Pump should be traced."
    ::= { oraPumpEntry  3 }

oraPumpTraceFile OBJECT-TYPE
    SYNTAX  DisplayString
    ACCESS  read-only
    STATUS  mandatory
    DESCRIPTION
           "Indicates the name of the trace file the pump created.
	  On an Unix platform, the default trace file name is
	  /$ORACLE_HOME/network/trace/pmp_PID.trc, where pid is the process
	  ID of the pump and $ORACLE_HOME is the path which the ORACLE_HOME
	  points to."
    ::= { oraPumpEntry  4 }

oraPumpActiveConnections OBJECT-TYPE
    SYNTAX  Gauge
    ACCESS  read-only
    STATUS  mandatory
    DESCRIPTION
           "The number of connections that are currently active."
    ::= { oraPumpEntry  5 }

oraPumpSuccessfulConnections OBJECT-TYPE
    SYNTAX  Counter
    ACCESS  read-only
    STATUS  mandatory
    DESCRIPTION
           "The total number of successful connections through the pump."
    ::= { oraPumpEntry  6 }

oraPumpFailedConnections OBJECT-TYPE
    SYNTAX  Counter
    ACCESS  read-only
    STATUS  mandatory
    DESCRIPTION
           "The total number of unsuccessful connections through the pump."
    ::= { oraPumpEntry  7 }

oraPumpAccumulatedBytesSent OBJECT-TYPE
    SYNTAX  Counter
    ACCESS  read-only
    STATUS  mandatory
    DESCRIPTION
           "The total number of bytes sent through the pump."
    ::= { oraPumpEntry  8 }

oraPumpCurrentBytesPerSecond OBJECT-TYPE
    SYNTAX  INTEGER
    ACCESS  read-only
    STATUS  mandatory
    DESCRIPTION
           "The current number of bytes sent per second through the pump."
    ::= { oraPumpEntry  9 }

oraPumpMaximumAverageBytes OBJECT-TYPE
    SYNTAX  INTEGER
    ACCESS  read-only
    STATUS  mandatory
    DESCRIPTION
           "The maximum average number of bytes sent through the pump."
    ::= { oraPumpEntry  10 }

oraPumpImmediateAverageBytes OBJECT-TYPE
    SYNTAX  INTEGER
    ACCESS  read-only
    STATUS  mandatory
    DESCRIPTION
           "The immediate average number of bytes sent through the pump."
    ::= { oraPumpEntry  11 }

oraPumpMaximumConnectTime OBJECT-TYPE
    SYNTAX  INTEGER
    ACCESS  read-only
    STATUS  mandatory
    DESCRIPTION
           "The maximum time in centi-seconds to establish a connection."
    ::= { oraPumpEntry  12 }

oraPumpMinimumConnectTime OBJECT-TYPE
    SYNTAX  INTEGER
    ACCESS  read-only
    STATUS  mandatory
    DESCRIPTION
           "The minimum time in centi-seconds to establish a connection."
    ::= { oraPumpEntry  13 }

oraPumpAverageConnectTime OBJECT-TYPE
    SYNTAX  INTEGER
    ACCESS  read-only
    STATUS  mandatory
    DESCRIPTION
           "The average time in centi-seconds to establish a connection."
    ::= { oraPumpEntry  14 }

oraPumpMaximumConnectDuration OBJECT-TYPE
    SYNTAX  INTEGER
    ACCESS  read-only
    STATUS  mandatory
    DESCRIPTION
           "The maximum connection duration time in centi-seconds.  This is the
	  elapsed time between a connection is established and before the
	  connection is terminated."
    ::= { oraPumpEntry  15 }

oraPumpMaximumBuffers OBJECT-TYPE
    SYNTAX  INTEGER
    ACCESS  read-write
    STATUS  mandatory
    DESCRIPTION
           "The maximum number of buffers available for use by connections
	   in the pump."
    ::= { oraPumpEntry  16 }

oraPumpBufferUtilization OBJECT-TYPE
    SYNTAX  Gauge
    ACCESS  read-only
    STATUS  mandatory
    DESCRIPTION
           "The pump buffer utilization in percentage."
    ::= { oraPumpEntry  17 }

oraPumpErrors OBJECT-TYPE
    SYNTAX  DisplayString
    ACCESS  read-only
    STATUS  mandatory
    DESCRIPTION
           "The error stack of a Pump when it fails."
    ::= { oraPumpEntry  18 }

oraPumpErrorMessage OBJECT-TYPE
    SYNTAX  DisplayString
    ACCESS  read-only
    STATUS  mandatory
    DESCRIPTION
           "The error message of a Pump when it fails."
    ::= { oraPumpEntry  19 }

oraPumpListenAddressTable OBJECT-TYPE
    SYNTAX  SEQUENCE OF OraPumpListenAddressEntry
    ACCESS  not-accessible
    STATUS  mandatory
    DESCRIPTION
           "The table of information about the addresses that a  
	   Pump is listening on."
    ::= { oraInterchangeObjects  10 }

oraPumpListenAddressEntry OBJECT-TYPE
    SYNTAX  OraPumpListenAddressEntry
    ACCESS  not-accessible
    STATUS  mandatory
    DESCRIPTION
           "An entry in the table associated with the addresses at which 
	   a Pump is listening on."
    INDEX   { applIndex,  oraPumpIndex,  oraPumpListenAddressIndex }
            C_NEXT_FUNC next_oraPumpListenAddressEntry
    ::= { oraPumpListenAddressTable  1 }

OraPumpListenAddressEntry ::=
    SEQUENCE {
        oraPumpListenAddressIndex
            INTEGER,

        oraPumpListenAddress
            DisplayString
    }

oraPumpListenAddressIndex OBJECT-TYPE
    SYNTAX  INTEGER
    ACCESS  read-only
    STATUS  mandatory
    DESCRIPTION
           "A numeric index, unique among all the listen addresses at which
	  a pump is listening on."
    ::= { oraPumpListenAddressEntry  1 }

oraPumpListenAddress OBJECT-TYPE
    SYNTAX  DisplayString
    ACCESS  read-only
    STATUS  mandatory
    DESCRIPTION
           "The address at which a Pump is listening on."
    ::= { oraPumpListenAddressEntry  2 }

oraPumpFailedAddressTable OBJECT-TYPE
    SYNTAX  SEQUENCE OF OraPumpFailedAddressEntry
    ACCESS  not-accessible
    STATUS  mandatory
    DESCRIPTION
           "The table of information about the addresses that a  
	   Pump fails to listen on."
    ::= { oraInterchangeObjects  11 }

oraPumpFailedAddressEntry OBJECT-TYPE
    SYNTAX  OraPumpFailedAddressEntry
    ACCESS  not-accessible
    STATUS  mandatory
    DESCRIPTION
           "An entry in the table associated with the addresses  
	   that a Pump fails to listen on."
    INDEX   { applIndex,  oraPumpIndex,  oraPumpFailedAddressIndex }
            C_NEXT_FUNC next_oraPumpFailedAddressEntry
    ::= { oraPumpFailedAddressTable  1 }

OraPumpFailedAddressEntry ::=
    SEQUENCE {
        oraPumpFailedAddressIndex
            INTEGER,

        oraPumpFailedAddress
            DisplayString
    }

oraPumpFailedAddressIndex OBJECT-TYPE
    SYNTAX  INTEGER
    ACCESS  read-only
    STATUS  mandatory
    DESCRIPTION
           "A numeric index, unique among all the addresses which 
	  a pump fails to listen on."
    ::= { oraPumpFailedAddressEntry  1 }

oraPumpFailedAddress OBJECT-TYPE
    SYNTAX  DisplayString
    ACCESS  read-only
    STATUS  mandatory
    DESCRIPTION
           "The address that a Pump fails to listen on."
    ::= { oraPumpFailedAddressEntry  2 }

oraConnectionTable OBJECT-TYPE
    SYNTAX  SEQUENCE OF OraConnectionEntry
    ACCESS  not-accessible
    STATUS  mandatory
    DESCRIPTION
           "The table of information about the status of a connection."
    ::= { oraInterchangeObjects  12 }

oraConnectionEntry OBJECT-TYPE
    SYNTAX  OraConnectionEntry
    ACCESS  not-accessible
    STATUS  mandatory
    DESCRIPTION
           "An entry in the table associated with a connection."
    INDEX   { applIndex,  oraPumpIndex,  oraConnectionIndex }
            C_NEXT_FUNC next_oraConnectionEntry
    ::= { oraConnectionTable  1 }

OraConnectionEntry ::=
    SEQUENCE {
        oraConnectionIndex
            INTEGER,

        oraConnectionPumpID
            INTEGER,

        oraConnectionIdleTime
            INTEGER,

        oraConnectionDuration
            INTEGER,

        oraConnectionSourceAddress
            DisplayString,

        oraConnectionDestinationAddress
            DisplayString
    }

oraConnectionIndex OBJECT-TYPE
    SYNTAX  INTEGER
    ACCESS  read-only
    STATUS  mandatory
    DESCRIPTION
           "A numeric index, unique among all the connections that a pump has."
    ::= { oraConnectionEntry  1 }

oraConnectionPumpID OBJECT-TYPE
    SYNTAX  INTEGER
    ACCESS  read-only
    STATUS  mandatory
    DESCRIPTION
           "The Pump ID of a connection."
    ::= { oraConnectionEntry  2 }

oraConnectionIdleTime OBJECT-TYPE
    SYNTAX  INTEGER
    ACCESS  read-write
    STATUS  mandatory
    DESCRIPTION
           "The number of minutes a connection can remain idle before
	   a Connection Manager will terminate it."
    ::= { oraConnectionEntry  3 }

oraConnectionDuration OBJECT-TYPE
    SYNTAX  INTEGER
    ACCESS  read-only
    STATUS  mandatory
    DESCRIPTION
           "The elapsed time is centi-seconds after a connection was established 
	   and before a connection is terminated."
    ::= { oraConnectionEntry  4 }

oraConnectionSourceAddress OBJECT-TYPE
    SYNTAX  DisplayString
    ACCESS  read-only
    STATUS  mandatory
    DESCRIPTION
           "The source address of a connect request."
    ::= { oraConnectionEntry  5 }

oraConnectionDestinationAddress OBJECT-TYPE
    SYNTAX  DisplayString
    ACCESS  read-only
    STATUS  mandatory
    DESCRIPTION
           "The destination address of a connect request."
    ::= { oraConnectionEntry  6 }

oraInterchgTraps OBJECT IDENTIFIER ::= { oraInterchangeMIB  2 }

oraNavigatorStateChange TRAP-TYPE
    ENTERPRISE    oraInterchgTraps 
    VARIABLES   { oraNavigatorState }
    DESCRIPTION
           "A navigatorStateChange trap signifies that a Navigator state 
           has been changed."
    ::= 1

oraCmanagerStateChange TRAP-TYPE
    ENTERPRISE    oraInterchgTraps 
    VARIABLES   { oraCmanagerState }
    DESCRIPTION
           "A cmanagerStateChange trap signifies that a Connection Manager 
           state has been changed."
    ::= 2

END
