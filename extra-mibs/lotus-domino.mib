-- Domino MIB Specification (the "Specification") Version 4.6
-- Copyright (c) 1994-1997 Lotus Development Corp.
--
--Use and restrictions. You are permitted to use, reproduce and distribute
--the Specification and this document ("Document"), provided you comply
--with the following terms.
--
--You shall distribute the Specification and Document with the text of this
--entire copyright notice and agreement. You may not modify, alter or create
--derivatives of the Specification or Document without prior written
--permission from Lotus. You may not loan or license the Specification or Document, or
--any copy.
--
--Ownership.   All intellectual property rights in the Specification and
--Document are owned by Lotus or its suppliers and are protected by United
--States and Canadian copyright laws, other applicable copyright laws, and
--international treaty provisions.
--Lotus retains all rights not expressly granted.
--
--No warranty. Lotus is supplying the Specification and Document "as is",
--without warranty, representation, promise or guarantee, either express or
--implied, statutory or otherwise, with respect to the Specification and
--Document, including their quality, performance, merchantability or fitness
--for a particular purpose.
--
--LIMITATION OF LIABILITY
--Because software is inherently complex and may not be completely free of
--errors, it is your responsibility to verify your work and to make backup
--copies, and Lotus will not be responsible for your failure to do so.  In
--no event will Lotus be liable for direct, indirect, special, incidental,
--or consequential damages arising out of this Agreement or out of the use
--Lotus products or services, including, without limitation, damages or
--costs relating to the loss of profits, business, goodwill, data or
--computer programs, even if advised of the possibility of such damages. The
--foregoing limitations shall not apply to claims relating to death or
--personal injury which arise out of products deemed to be consumer goods
--under applicable law.  Some states or provinces do not allow the exclusion
--or limitation of implied warranties or limitation of liability for
--incidental or consequential damages, so the above exclusion or limitation
--may not apply to you.
--
--For U.S. customers: Should you have any questions concerning this
--Agreement or Lotus software use policies, write to Inside Sales and
--Service, Lotus Development Corporation, 55 Cambridge Parkway,
--Cambridge, MA  02142, or call 1-800-343-5414.

NOTES-MIB DEFINITIONS ::= BEGIN

IMPORTS
   OBJECT-TYPE               FROM RFC-1212
   DisplayString             FROM RFC1213-MIB;

--Definitions for Lotus enterprise branch and Notes sub-branch

Lotus                   OBJECT IDENTIFIER ::= { enterprises 334 }
Notes                   OBJECT IDENTIFIER ::= { Lotus 72 }
NotesPump               OBJECT IDENTIFIER ::= { Lotus 73 }

--Definitions of Notes main groups

lnInfo                  OBJECT IDENTIFIER ::= { Notes 1 }
lnControl               OBJECT IDENTIFIER ::= { Notes 2 }
lnInterceptor           OBJECT IDENTIFIER ::= { Notes 3 }
lnUnix                  OBJECT IDENTIFIER ::= { Notes 4 }
MPAInfo                 OBJECT IDENTIFIER ::= { Notes 100 }

--Definitions of sub-groups of the lnInfo group

lnStats                 OBJECT IDENTIFIER ::= { lnInfo 1 }

--Definitions of sub-groups of the lnStats group

lnMail                  OBJECT IDENTIFIER ::= { lnStats 4 }
lnReplica               OBJECT IDENTIFIER ::= { lnStats 5 }
lnServer                OBJECT IDENTIFIER ::= { lnStats 6 }
lnComm                  OBJECT IDENTIFIER ::= { lnStats 7 }
lnDisk                  OBJECT IDENTIFIER ::= { lnStats 8 }
lnMem                   OBJECT IDENTIFIER ::= { lnStats 9 }
lnDatabase              OBJECT IDENTIFIER ::= { lnStats 10 }
lnAgentMgr              OBJECT IDENTIFIER ::= { lnStats 11 }
lnMTA                   OBJECT IDENTIFIER ::= { lnStats 12 }
lnWeb                   OBJECT IDENTIFIER ::= { lnStats 13 }
lnObject                OBJECT IDENTIFIER ::= { lnStats 14 }
lnDomino                OBJECT IDENTIFIER ::= { lnStats 15 }
lnCalendar              OBJECT IDENTIFIER ::= { lnStats 16 }
lnCollector             OBJECT IDENTIFIER ::= { lnStats 17 }

--Definitions of sub-groups of the lnServer group

lnServerTask            OBJECT IDENTIFIER ::= { lnServer 1 }
lnServerInfo            OBJECT IDENTIFIER ::= { lnServer 2 }
lnServerStats           OBJECT IDENTIFIER ::= { lnServer 3 }
lnCluster               OBJECT IDENTIFIER ::= { lnServer 4 }


--Definitions of sub-groups of the lnCluster group

lnOpenRedirects         OBJECT IDENTIFIER ::= { lnCluster 8  }
lnOpenRequest           OBJECT IDENTIFIER ::= { lnCluster 9  }
lnClusterTrans          OBJECT IDENTIFIER ::= { lnCluster 10 }

--Definitions of sub-groups of the lnReplica group

lnReplicaCluster        OBJECT IDENTIFIER ::= { lnReplica 6 }


--  ******************************************************************
--  Define information provided to us by the Main Proxy Agent.
--  ******************************************************************

lnMainProxyAgentVersion OBJECT-TYPE
    SYNTAX DisplayString
    ACCESS read-only
    STATUS mandatory
    DESCRIPTION
      "Information relevant to the Lotus Main SNMP Proxy Agent"
    ::= {MPAInfo 1 }


--  ******************************************************************
--                         LNSTATS GROUP
--  ******************************************************************

--The full (uninterpreted) statistics structure table

lnAllStatsTable OBJECT-TYPE
    SYNTAX SEQUENCE OF lnAllStatsEntry
    ACCESS not-accessible
    STATUS mandatory
    DESCRIPTION
           "A table containing a one statistic per entry view of the
            entire Notes server statistics structure."
    ::= { lnStats 1 }

lnAllStatsEntry OBJECT-TYPE
    SYNTAX lnAllStatsEntry
    ACCESS not-accessible
    STATUS mandatory
    DESCRIPTION
           "The entry type definition for the lnAllStatsTable."
    INDEX { lnStatisticIndex }
    ::= { lnAllStatsTable 1 }

lnAllStatsEntry ::= SEQUENCE {
    lnStatisticIndex        INTEGER,
    lnStatisticString       DisplayString
}

lnStatisticIndex OBJECT-TYPE
    SYNTAX INTEGER (1..2147483647)
    ACCESS read-only
    STATUS mandatory
    DESCRIPTION
           "A unique value for each statistic in the Notes server
            statistics structure."
    ::= { lnAllStatsEntry 1 }

lnStatisticString OBJECT-TYPE
    SYNTAX DisplayString
    ACCESS read-only
    STATUS mandatory
    DESCRIPTION
           "A string describing one statistic from the Notes
            Server statistics structure."
    ::= { lnAllStatsEntry 2 }

--Times related to statistics

lnStatsStartTime OBJECT-TYPE
    SYNTAX INTEGER (0..4294967295)
    ACCESS read-only
    STATUS mandatory
    DESCRIPTION
           "Time and date at which the statistics agent was
            last started.  Represented as the number of seconds
            since midnight 1/1/70 GMT (UNIX epoch)."
    ::= { lnStats 2 }

lnStatsCurrentTime OBJECT-TYPE
    SYNTAX INTEGER (0..4294967295)
    ACCESS read-only
    STATUS mandatory
    DESCRIPTION
           "Time and date of the last statistics update.  Represented
            as the number of seconds since midnight 1/1/70 GMT
            (UNIX epoch)."
    ::= { lnStats 3 }

--  ******************************************************************
--                           LNMAIL GROUP
--  ******************************************************************

lnDeadMail OBJECT-TYPE
    SYNTAX INTEGER (0..4294967295)
    ACCESS read-only
    STATUS optional
    DESCRIPTION
           "Number of dead (undeliverable) mail messages."
    ::= { lnMail 1 }

lnDeliveredMail OBJECT-TYPE
    SYNTAX INTEGER (0..4294967295)
    ACCESS read-only
    STATUS optional
    DESCRIPTION
           "Number of messges received by router."
    ::= { lnMail 2 }

lnTotalMailFailures OBJECT-TYPE
    SYNTAX INTEGER (0..4294967295)
    ACCESS read-only
    STATUS optional
    DESCRIPTION
           "Total number of routing failures since the
            server started."
    ::= { lnMail 3 }

lnTotalRoutedMail OBJECT-TYPE
    SYNTAX INTEGER (0..4294967295)
    ACCESS read-only
    STATUS optional
    DESCRIPTION
           "Total number of mail messages routed since the
            server started."
    ::= { lnMail 4 }

lnTransferredMail OBJECT-TYPE
    SYNTAX INTEGER (0..4294967295)
    ACCESS read-only
    STATUS optional
    DESCRIPTION
           "Number of messages router attempted to transfer."
    ::= { lnMail 5 }

lnWaitingMail OBJECT-TYPE
    SYNTAX INTEGER (0..4294967295)
    ACCESS read-only
    STATUS optional
    DESCRIPTION
           "Number of mail messages waiting to be routed."
    ::= { lnMail 6 }

lnNumWaitingRecipients OBJECT-TYPE
    SYNTAX INTEGER (0..4294967295)
    ACCESS read-only
    STATUS optional
    DESCRIPTION
           "Number of pending mail messages awaiting local delivery."
    ::= { lnMail 7 }

lnMailDomain OBJECT-TYPE
    SYNTAX DisplayString
    ACCESS read-only
    STATUS optional
    DESCRIPTION
           "Notes server's mail domain."
    ::= { lnMail 8 }

lnAverageMailDeliverTime OBJECT-TYPE
    SYNTAX INTEGER (0..4294967295)
    ACCESS read-only
    STATUS optional
    DESCRIPTION
           "Average time for mail delivery in seconds."
    ::= { lnMail 9 }

lnAverageMailServerHops OBJECT-TYPE
    SYNTAX INTEGER (0..4294967295)
    ACCESS read-only
    STATUS optional
    DESCRIPTION
           "Average number of server hops for mail delivery."
    ::= { lnMail 10 }

lnAverageMailSizeDelivered OBJECT-TYPE
    SYNTAX INTEGER (0..4294967295)
    ACCESS read-only
    STATUS optional
    DESCRIPTION
           "Average size of mail messages delivered in bytes."
    ::= { lnMail 11 }

lnMaximumMailDeliverTime OBJECT-TYPE
    SYNTAX INTEGER (0..4294967295)
    ACCESS read-only
    STATUS optional
    DESCRIPTION
           "Maximum time for mail delivery in seconds."
    ::= { lnMail 12 }

lnMaximumMailServerHops OBJECT-TYPE
    SYNTAX INTEGER (0..4294967295)
    ACCESS read-only
    STATUS optional
    DESCRIPTION
           "Maximum number of server hops for mail delivery."
    ::= { lnMail 13 }

lnMaximumMailSizeDelivered OBJECT-TYPE
    SYNTAX INTEGER (0..4294967295)
    ACCESS read-only
    STATUS optional
    DESCRIPTION
           "Maximum size of mail delivered in bytes."
    ::= { lnMail 14 }

lnMinimumMailDeliverTime OBJECT-TYPE
    SYNTAX INTEGER (0..4294967295)
    ACCESS read-only
    STATUS optional
    DESCRIPTION
           "Minimum time for mail delivery in seconds."
    ::= { lnMail 15 }

lnMinimumMailServerHops OBJECT-TYPE
    SYNTAX INTEGER (0..4294967295)
    ACCESS read-only
    STATUS optional
    DESCRIPTION
           "Minimum number of server hops for mail delivery."
    ::= { lnMail 16 }

lnMinimumMailSizeDelivered OBJECT-TYPE
    SYNTAX INTEGER (0..4294967295)
    ACCESS read-only
    STATUS optional
    DESCRIPTION
           "Minimum size of mail delivered in bytes."
    ::= { lnMail 17 }

lnTotalKBTransferred OBJECT-TYPE
    SYNTAX INTEGER (0..4294967295)
    ACCESS read-only
    STATUS optional
    DESCRIPTION
           "Total mail transferred in kilobytes."
    ::= { lnMail 18 }

lnMailTransferFailures OBJECT-TYPE
    SYNTAX INTEGER (0..4294967295)
    ACCESS read-only
    STATUS optional
    DESCRIPTION
           "Number of mail messages the router was unable to transfer."
    ::= { lnMail 19 }

--  ******************************************************************
--                        LNREPLICA GROUP
--  ******************************************************************

lnRepDocsAdded OBJECT-TYPE
    SYNTAX INTEGER (0..4294967295)
    ACCESS read-only
    STATUS optional
    DESCRIPTION
           "Number of  docs added via replication since server
            was started."
    ::= { lnReplica 1 }

lnRepDocsDeleted OBJECT-TYPE
    SYNTAX INTEGER (0..4294967295)
    ACCESS read-only
    STATUS optional
    DESCRIPTION
           "Number of docs deleted via replication since server
            was started."
    ::= { lnReplica 2 }

lnRepDocsUpdated OBJECT-TYPE
    SYNTAX INTEGER (0..4294967295)
    ACCESS read-only
    STATUS optional
    DESCRIPTION
           "Number of docs updated via replication since server
            was started."
    ::= { lnReplica 3 }

lnRepFailed OBJECT-TYPE
    SYNTAX INTEGER (0..4294967295)
    ACCESS read-only
    STATUS optional
    DESCRIPTION
           "Number of replications that generated an error."
    ::= { lnReplica 4 }

lnRepSuccessful OBJECT-TYPE
    SYNTAX INTEGER (0..4294967295)
    ACCESS read-only
    STATUS optional
    DESCRIPTION
           "Number of successful replications."
    ::= { lnReplica 5 }

--  ******************************************************************
--                      LNREPLICACLUSTER GROUP
--  ******************************************************************

lnRepClusterDocsAdded OBJECT-TYPE
    SYNTAX INTEGER (0..4294967295)
    ACCESS read-only
    STATUS optional
    DESCRIPTION
           "The number of documents added by the cluster replicator"
    ::= { lnReplicaCluster 1 }

lnRepClusterDocsDeleted OBJECT-TYPE
    SYNTAX INTEGER (0..4294967295)
    ACCESS read-only
    STATUS optional
    DESCRIPTION
           "The number of documents deleted by the cluster replicator"
    ::= { lnReplicaCluster 2 }

lnRepClusterDocsUpdated OBJECT-TYPE
    SYNTAX INTEGER (0..4294967295)
    ACCESS read-only
    STATUS optional
    DESCRIPTION
           "The number of documents updated by the cluster replicator"
    ::= { lnReplicaCluster 3 }

lnRepClusterFailed OBJECT-TYPE
    SYNTAX INTEGER (0..4294967295)
    ACCESS read-only
    STATUS optional
    DESCRIPTION
           "The number of failed replications since server startup."
    ::= { lnReplicaCluster 4 }

lnRepClusterFilesLocal OBJECT-TYPE
    SYNTAX INTEGER (0..4294967295)
    ACCESS read-only
    STATUS optional
    DESCRIPTION
           "The number of databases on the current server for which
            there are replicas on other servers in the cluster."
    ::= { lnReplicaCluster 5 }

lnRepClusterFilesRemote OBJECT-TYPE
    SYNTAX INTEGER (0..4294967295)
    ACCESS read-only
    STATUS optional
    DESCRIPTION
           "The number of databases on other servers to which the
            cluster replicator pushes changes."
    ::= { lnReplicaCluster 6 }

lnRepClusterRetrySkipped OBJECT-TYPE
    SYNTAX INTEGER (0..4294967295)
    ACCESS read-only
    STATUS optional
    DESCRIPTION
           "The number of times the cluster replicator did not attempt
            to replicate a database.  The retry is skipped when the
            destination server is known to be unreachable, or the database
            is waiting for another retry attempt."
    ::= { lnReplicaCluster 7 }

lnRepClusterRetryWaiting OBJECT-TYPE
    SYNTAX INTEGER (0..4294967295)
    ACCESS read-only
    STATUS optional
    DESCRIPTION
           "The number of replicas that are waiting for retry attempts."
    ::= { lnReplicaCluster 8 }

lnRepClusterSecondsOnQueue OBJECT-TYPE
    SYNTAX INTEGER (0..4294967295)
    ACCESS read-only
    STATUS optional
    DESCRIPTION
           "The amount of time in seconds that the last database
            replicated spent on the work queue."
    ::= { lnReplicaCluster 9 }

lnRepClusterSecondsOnQueueAvg OBJECT-TYPE
    SYNTAX INTEGER (0..4294967295)
    ACCESS read-only
    STATUS optional
    DESCRIPTION
           "The average amount of time in seconds that a database
            spent on the work queue."
    ::= { lnReplicaCluster 10 }

lnRepClusterSecondsOnQueueMax OBJECT-TYPE
    SYNTAX INTEGER (0..4294967295)
    ACCESS read-only
    STATUS optional
    DESCRIPTION
           "The maximum amount of time in seconds that a database
            spent on the work queue."
    ::= { lnReplicaCluster 11 }

lnRepClusterServers OBJECT-TYPE
    SYNTAX INTEGER (0..4294967295)
    ACCESS read-only
    STATUS optional
    DESCRIPTION
           "The number of other servers in the cluster that are receiving
            replications from this server."
    ::= { lnReplicaCluster 12 }

lnRepClusterSessionBytesIn OBJECT-TYPE
    SYNTAX INTEGER (0..4294967295)
    ACCESS read-only
    STATUS optional
    DESCRIPTION
           "The total number of bytes received during cluster replication"
    ::= { lnReplicaCluster 13 }

lnRepClusterSessionBytesOut OBJECT-TYPE
    SYNTAX INTEGER (0..4294967295)
    ACCESS read-only
    STATUS optional
    DESCRIPTION
           "The total number of bytes sent during cluster replication"
    ::= { lnReplicaCluster 14 }

lnRepClusterSuccessful OBJECT-TYPE
    SYNTAX INTEGER (0..4294967295)
    ACCESS read-only
    STATUS optional
    DESCRIPTION
           "The number of successful replications since server startup."
    ::= { lnReplicaCluster 15 }

lnRepClusterWorkQueueDepth OBJECT-TYPE
    SYNTAX INTEGER (0..4294967295)
    ACCESS read-only
    STATUS optional
    DESCRIPTION
           "The current number of databases awaiting replication by
            the cluster replicator."
    ::= { lnReplicaCluster 16 }

lnRepClusterWorkQueueDepthAvg OBJECT-TYPE
    SYNTAX INTEGER (0..4294967295)
    ACCESS read-only
    STATUS optional
    DESCRIPTION
           "The average work queue depth since server startup."
    ::= { lnReplicaCluster 17 }

lnRepClusterWorkQueueDepthMax OBJECT-TYPE
    SYNTAX INTEGER (0..4294967295)
    ACCESS read-only
    STATUS optional
    DESCRIPTION
           "The maximum depth reached by the work queue since server startup."
    ::= { lnReplicaCluster 18 }


--  ******************************************************************
--                       LNSERVERTASK GROUP
--  ******************************************************************

lnTaskCount OBJECT-TYPE
    SYNTAX INTEGER (0..4294967295)
    ACCESS read-only
    STATUS mandatory
    DESCRIPTION
           "Number of Notes server tasks currently executing."
    ::= { lnServerTask 1 }

lnTaskTable OBJECT-TYPE
    SYNTAX SEQUENCE OF lnTaskEntry
    ACCESS not-accessible
    STATUS mandatory
    DESCRIPTION
           "A table containing one entry for each Notes server
            task that is actually running."
    ::= { lnServerTask 2 }

lnTaskEntry OBJECT-TYPE
    SYNTAX lnTaskEntry
    ACCESS not-accessible
    STATUS mandatory
    DESCRIPTION
           "The entry type definition for the lnTaskTable."
    INDEX { lnTaskIndex }
    ::= { lnTaskTable 1 }

lnTaskEntry ::= SEQUENCE {
    lnTaskIndex             INTEGER,
    lnTaskType              INTEGER,
    lnTaskData              DisplayString,
    lnTaskName              DisplayString
}

lnTaskIndex OBJECT-TYPE
    SYNTAX INTEGER (1..2147483647)
    ACCESS read-only
    STATUS mandatory
    DESCRIPTION
           "A unique value for each entry in lnTaskTable."
    ::= { lnTaskEntry 1 }

lnTaskType OBJECT-TYPE
    SYNTAX INTEGER {
      DatabaseServer(1),
      Event(2),
      Reporter(3),
      Replicator(4),
      Indexer(5),
      Router(6),
      EventInterceptor(7),
      QuerySetHandler(8),
      ReflectorAgent(9),
      WebRetriever(10),
      CalendarConnector(11),
      ScheduleManager(12),
      UnknownAddin(13),
      AdminProcess(14),
      HTTPWebServer(15),
      Chronos(16),
      Collector(17),
      Inotes(18),
      Billing(19),
      ClusterReplicator(20),
      ClusterDbDirMgr(21),
      ClusterAdmin(22),
      AgentManager(23),
      Cataloger(24),
      DatabaseCompactor(25),
      Designer(26),
      ObjectStoreMgr(27),
      POP3Server(28),
      Statistics(29),
      Stats(30),
      DatabaseFixup(31),
      INNEWS(32),
      WebPublisher(33),
      CCMailMTA(34),
      SMTPMTA(35),
      X400MTA(36),
      LDAPServer(37),
      NNTPServer(38),
      IMAPServer(39),
      IMAP4Server(40)
    }
    ACCESS read-only
    STATUS mandatory
    DESCRIPTION
           "The type of server task being represented by this entry"
    ::= { lnTaskEntry 2 }

lnTaskData OBJECT-TYPE
    SYNTAX DisplayString
    ACCESS read-only
    STATUS mandatory
    DESCRIPTION
           "Information associated with this task entry.  See the
            description for lnTaskType."
    ::= { lnTaskEntry 3 }

lnTaskName OBJECT-TYPE
        SYNTAX DisplayString
        ACCESS read-only
        STATUS mandatory
        DESCRIPTION
               "The actual name of the task as it appears in the
               SERVER.TASK statistic on the server"
    ::= { lnTaskEntry 4 }

lnReplicatorStatus OBJECT-TYPE
    SYNTAX DisplayString
    ACCESS read-only
    STATUS mandatory
    DESCRIPTION
           "Status of the Replicator task.  Provided as a separate MIB
            variable for the sake of efficiency."
    ::= { lnServerTask 3 }

lnRouterStatus OBJECT-TYPE
    SYNTAX DisplayString
    ACCESS read-only
    STATUS mandatory
    DESCRIPTION
           "Status of the Router task.  Provided as a separate MIB
            variable for the sake of efficiency."
    ::= { lnServerTask 4 }

lnEventStatus OBJECT-TYPE
    SYNTAX DisplayString
    ACCESS read-only
    STATUS mandatory
    DESCRIPTION
           "Status of the Event task.  Provided as a separate MIB
            variable for the sake of efficiency."
    ::= { lnServerTask 5 }

--  ******************************************************************
--                      LNSERVERINFO GROUP
--  ******************************************************************

lnServerName OBJECT-TYPE
    SYNTAX DisplayString
    ACCESS read-only
    STATUS mandatory
    DESCRIPTION
           "Server Name."
    ::= { lnServerInfo 1 }

lnServerTitle OBJECT-TYPE
    SYNTAX DisplayString
    ACCESS read-only
    STATUS optional
    DESCRIPTION
           "Title assigned to this server."
    ::= { lnServerInfo 2 }

lnServerAdministrators OBJECT-TYPE
    SYNTAX DisplayString
    ACCESS read-only
    STATUS mandatory
    DESCRIPTION
           "Contents of Administrator field from server record in
            Public Address book."
    ::= { lnServerInfo 3 }

lnServerNotesVersion OBJECT-TYPE
    SYNTAX DisplayString
    ACCESS read-only
    STATUS mandatory
    DESCRIPTION
           "Release of the Notes server that is running."
    ::= { lnServerInfo 4 }

lnServerSystemVersion OBJECT-TYPE
    SYNTAX DisplayString
    ACCESS read-only
    STATUS mandatory
    DESCRIPTION
           "Release of the Operating System running on the server."
    ::= { lnServerInfo 5 }

lnServerBootID OBJECT-TYPE
    SYNTAX INTEGER (0..4294967295)
    ACCESS read-only
    STATUS mandatory
    DESCRIPTION
           "Unique number identifying the time this server was last booted."
    ::= { lnServerInfo 6 }

lnServerDataPath OBJECT-TYPE
    SYNTAX DisplayString
    ACCESS read-only
    STATUS optional
    DESCRIPTION
           "Drive and directory defined as this server's data directory."
    ::= { lnServerInfo 7 }

lnServerSwapPath OBJECT-TYPE
    SYNTAX DisplayString
    ACCESS read-only
    STATUS optional
    DESCRIPTION
           "Drive and directory for this server's swap file
            (NOTE:  this stat relies on the NOTES.INI variable
            'SWAPPATH' if config.sys contains a swap path
            different from the default.)"
    ::= { lnServerInfo 8 }

lnServerRS232Ports OBJECT-TYPE
    SYNTAX INTEGER (0..4294967295)
    ACCESS read-only
    STATUS optional
    DESCRIPTION
           "Number of RS232 ports on this server."
    ::= { lnServerInfo 9 }

lnServerCoprocessor OBJECT-TYPE
    SYNTAX INTEGER {
      No(1),
      Yes(2)
    }
    ACCESS read-only
    STATUS optional
    DESCRIPTION
           "Returns 'Yes', if server is a 486 or 386 w/ 387, otherwise, Returns 'No'."
    ::= { lnServerInfo 10 }

lnServerOS OBJECT-TYPE
    SYNTAX INTEGER {
      OS2(1),
      NetWare(2),
      WindowsNT(3),
      Unix(4)
    }
    ACCESS read-only
    STATUS mandatory
    DESCRIPTION
           "Operating System the current Notes server is running."
    ::= { lnServerInfo 11 }

lnServerCPUCount OBJECT-TYPE
    SYNTAX INTEGER (0..4294967295)
    ACCESS read-only
    STATUS mandatory
    DESCRIPTION
           "The number of processors installed on this server."
    ::= { lnServerInfo 12 }

lnServerCPUType OBJECT-TYPE
    SYNTAX DisplayString
    ACCESS read-only
    STATUS optional
    DESCRIPTION
           "The type of processor installed on the server (386,486, Pentium, etc)."
    ::= { lnServerInfo 13 }

lnServerUsersTable OBJECT-TYPE
    SYNTAX SEQUENCE OF lnServerUsersEntry
    ACCESS not-accessible
    STATUS optional
    DESCRIPTION
           "A table containing one entry for each Notes user
            on the server."
    ::= { lnServerInfo 14 }

lnServerPorts OBJECT-TYPE
    SYNTAX DisplayString
    ACCESS read-only
    STATUS optional
    DESCRIPTION
           "A list of ports on the server."
    ::= { lnServerInfo 15 }

lnServerPoweredBy OBJECT-TYPE
    SYNTAX DisplayString
    ACCESS read-only
    STATUS optional
    DESCRIPTION
           "Indicates what is powering the Domino server.  A value here
            would indicate the system is running Release 4.5 or better
            of the Domino server.  Value should = Notes"
    ::= { lnServerInfo 16 }

lnServerUsersEntry OBJECT-TYPE
    SYNTAX lnServerUsersEntry
    ACCESS not-accessible
    STATUS mandatory
    DESCRIPTION
           "The entry type definition for the lnServerUsersTable."
    INDEX { lnServerUsersIndex }
    ::= { lnServerUsersTable 1 }

lnServerUsersEntry ::= SEQUENCE {
    lnServerUsersIndex        INTEGER,
    lnServerUserName          DisplayString,
    lnServerUserSessionID     DisplayString,
    lnServerUserAccessedDBs   INTEGER
}

lnServerUsersIndex OBJECT-TYPE
    SYNTAX INTEGER (1..2147483647)
    ACCESS read-only
    STATUS mandatory
    DESCRIPTION
           "A unique value for each entry in lnServerUsersTable."
    ::= { lnServerUsersEntry 1 }

lnServerUserName OBJECT-TYPE
    SYNTAX DisplayString
    ACCESS read-only
    STATUS mandatory
    DESCRIPTION
           "Notes UserName of server user."
    ::= { lnServerUsersEntry 2 }

lnServerUserSessionID OBJECT-TYPE
    SYNTAX DisplayString
    ACCESS read-only
    STATUS mandatory
    DESCRIPTION
           "The user's Notes session ID."
    ::= { lnServerUsersEntry 3 }

lnServerUserAccessedDBs OBJECT-TYPE
    SYNTAX INTEGER (0..4294967295)
    ACCESS read-only
    STATUS mandatory
    DESCRIPTION
           "The number of databases accessed by the users."
    ::= { lnServerUsersEntry 4 }


--  ******************************************************************
--                      LNSERVERSTATS GROUP
--  ******************************************************************

lnServerDroppedSessions OBJECT-TYPE
    SYNTAX INTEGER (0..4294967295)
    ACCESS read-only
    STATUS optional
    DESCRIPTION
           "Number of dropped sessions."
    ::= { lnServerStats 1 }

lnServerTransPerMin OBJECT-TYPE
    SYNTAX INTEGER (0..4294967295)
    ACCESS read-only
    STATUS optional
    DESCRIPTION
           "Average number of transactions per minute since the
            server was started."
    ::= { lnServerStats 2 }

lnServerTransPerMinPeak OBJECT-TYPE
    SYNTAX INTEGER (0..4294967295)
    ACCESS read-only
    STATUS optional
    DESCRIPTION
           "Peak number of transactions that took place in any
            given minute since the server was started."
    ::= { lnServerStats 3 }

lnServerTransPerMinPeakTime OBJECT-TYPE
    SYNTAX INTEGER (0..4294967295)
    ACCESS read-only
    STATUS optional
    DESCRIPTION
           "Date and time when the peak number of transactions
            per minute was last reached.  Represented as the number
            of seconds since midnight 1/1/70 GMT (UNIX epoch)."
    ::= { lnServerStats 4 }

lnServerTransTotal OBJECT-TYPE
    SYNTAX INTEGER (0..4294967295)
    ACCESS read-only
    STATUS optional
    DESCRIPTION
           "Total number of transactions the server has completed
            since it was started."
    ::= { lnServerStats 5 }

lnServerUsers OBJECT-TYPE
    SYNTAX INTEGER (0..4294967295)
    ACCESS read-only
    STATUS optional
    DESCRIPTION
           "Number of users with sessions open on the server."
    ::= { lnServerStats 6 }

lnServerUsers1MinPeak OBJECT-TYPE
    SYNTAX INTEGER (0..4294967295)
    ACCESS read-only
    STATUS optional
    DESCRIPTION
           "The peak number of concurrent users active
            within the last minute."
    ::= { lnServerStats 7 }

lnServerUsers1MinPeakTime OBJECT-TYPE
    SYNTAX INTEGER (1..4294967295)
    ACCESS read-only
    STATUS optional
    DESCRIPTION
           "Date and time when the peak number of active concurrent
            users were reached within the last minute.  Represented as
            the number of seconds since midnight 1/1/70 GMT (UNIX epoch)."
    ::= { lnServerStats 8 }

lnServerUsers5MinPeak OBJECT-TYPE
    SYNTAX INTEGER (0..4294967295)
    ACCESS read-only
    STATUS optional
    DESCRIPTION
           "The peak number of concurrent users that were active
            within the last five minutes."
    ::= { lnServerStats 9 }

lnServerUsers5MinPeakTime OBJECT-TYPE
    SYNTAX INTEGER (1..4294967295)
    ACCESS read-only
    STATUS optional
    DESCRIPTION
           "Date and time when the peak number of active concurrent
            users were reached within the last five minutes.  Represented
            as the number of seconds since midnight 1/1/70 GMT (UNIX epoch)."
    ::= { lnServerStats 10 }

lnServerUsersPeak OBJECT-TYPE
    SYNTAX INTEGER (0..4294967295)
    ACCESS read-only
    STATUS optional
    DESCRIPTION
           "The peak number of concurrent users with open sessions
            since the server was started."
    ::= { lnServerStats 11 }

lnServerUsersPeakTime OBJECT-TYPE
    SYNTAX INTEGER (1..4294967295)
    ACCESS read-only
    STATUS optional
    DESCRIPTION
           "Date and time when the peak number of concurrent users
            with open sessions was last reached.  Represented as the
            number of seconds since midnight 1/1/70 GMT (UNIX epoch)."
    ::= { lnServerStats 12 }

lnServerOpenReqMaxUsers OBJECT-TYPE
    SYNTAX INTEGER (0..4294967295)
    ACCESS read-only
    STATUS optional
    DESCRIPTION
           "The number of times that a client has attempted to open
            a database on this server when the server was at its
            MAXUSERS limit."
    ::= { lnServerStats 13 }

lnServerOpenReqPreV4Client OBJECT-TYPE
    SYNTAX INTEGER (0..4294967295)
    ACCESS read-only
    STATUS optional
    DESCRIPTION
           "The number of times Notes Release 4.0 (or higher)
            clients have attempted to open a database on this server."
    ::= { lnServerStats 14 }

lnServerOpenReqRestricted OBJECT-TYPE
    SYNTAX INTEGER (0..4294967295)
    ACCESS read-only
    STATUS optional
    DESCRIPTION
           "The number of times that a client has attempted to open
            a database on this server when the server was RESTRICTED."
    ::= { lnServerStats 15 }

lnServerOpenReqV4Client OBJECT-TYPE
    SYNTAX INTEGER (0..4294967295)
    ACCESS read-only
    STATUS optional
    DESCRIPTION
           "The number of times Notes Clients post Release 4.0 have
            attempted to open a database on this server."
    ::= { lnServerStats 16 }

lnServerBusyTimeQueryReceivedCount OBJECT-TYPE
    SYNTAX INTEGER (0..4294967295)
    ACCESS read-only
    STATUS optional
    DESCRIPTION
           "The number of external 'busytime' queries the server has received."
    ::= { lnServerStats 17 }

lnServerBusyTimeQueryRetObjSched OBJECT-TYPE
    SYNTAX INTEGER (0..4294967295)
    ACCESS read-only
    STATUS optional
    DESCRIPTION
     "The number of schedules that were returned by queries counted
      by  lnServerBusyTimeQueriesReceivedCount"
    ::= { lnServerStats 18 }

--  ******************************************************************
--                         LNCOMM GROUP
--  ******************************************************************

lnNumClosedOldSessions OBJECT-TYPE
    SYNTAX INTEGER (0..4294967295)
    ACCESS read-only
    STATUS optional
    DESCRIPTION
           "Number of sessions dropped because of too many
            concurrent users."
    ::= { lnComm 1 }

lnNetbiosTable OBJECT-TYPE
    SYNTAX SEQUENCE OF lnNetbiosEntry
    ACCESS not-accessible
    STATUS mandatory
    DESCRIPTION
           "A table containing one entry for each active NetBIOS
            port on the server. Notes R3 only."
    ::= { lnComm 2 }

lnNetbiosEntry OBJECT-TYPE
    SYNTAX lnNetbiosEntry
    ACCESS not-accessible
    STATUS mandatory
    DESCRIPTION
           "The entry type definition for the lnNetbiosTable, Notes R3"
    INDEX { lnNBIndex }
    ::= { lnNetbiosTable 1 }

lnNetbiosEntry ::= SEQUENCE {
    lnNBIndex                  INTEGER,
    lnNBPort                   DisplayString,
    lnNBUnitNumber             INTEGER,
    lnNBMajVersion             INTEGER,
    lnNMMinVersion             INTEGER,
    lnNBReportPeriod           INTEGER,
    lnNBInUseSessions          INTEGER,
    lnNBMaxSessions            INTEGER,
    lnNBAvailCmdBlocks         INTEGER,
    lnNBTotalCmdBlocks         INTEGER,
    lnNBPacketSize             INTEGER,
    lnNBReceivedPackets        INTEGER,
    lnNBSentPackets            INTEGER,
    lnNBAbortedTransmissions   INTEGER,
    lnNBRetriedTransmissions   INTEGER,
    lnNBAlignmentErrors        INTEGER,
    lnNBCollisionErrors        INTEGER,
    lnNBCRCErrors              INTEGER
}

lnNBIndex OBJECT-TYPE
    SYNTAX INTEGER (1..2147483647)
    ACCESS read-only
    STATUS mandatory
    DESCRIPTION
           "A unique value for each entry in lnNetbiosTable."
    ::= { lnNetbiosEntry 1 }

lnNBPort OBJECT-TYPE
    SYNTAX DisplayString
    ACCESS read-only
    STATUS mandatory
    DESCRIPTION
           "NetBIOS port associated with this table entry."
    ::= { lnNetbiosEntry 2 }

lnNBUnitNumber OBJECT-TYPE
    SYNTAX INTEGER (0..4294967295)
    ACCESS read-only
    STATUS mandatory
    DESCRIPTION
           "Unit number for this NetBIOS port."
    ::= { lnNetbiosEntry 3 }

lnNBMajVersion OBJECT-TYPE
    SYNTAX INTEGER (0..4294967295)
    ACCESS read-only
    STATUS mandatory
    DESCRIPTION
           "Major version number of the NetBIOS driver being run on
            this port."
    ::= { lnNetbiosEntry 4 }

lnNMMinVersion OBJECT-TYPE
    SYNTAX INTEGER (0..4294967295)
    ACCESS read-only
    STATUS mandatory
    DESCRIPTION
           "Minor version number of the NetBIOS driver being run on
            this port."
    ::= { lnNetbiosEntry 5 }

lnNBReportPeriod OBJECT-TYPE
    SYNTAX INTEGER (0..4294967295)
    ACCESS read-only
    STATUS mandatory
    DESCRIPTION
           "Period of time over which the statistics for this port have
            been accumulating."
    ::= { lnNetbiosEntry 6 }

lnNBInUseSessions OBJECT-TYPE
    SYNTAX INTEGER (0..4294967295)
    ACCESS read-only
    STATUS mandatory
    DESCRIPTION
           "Number of NetBIOS sessions currently in use."
    ::= { lnNetbiosEntry 7 }

lnNBMaxSessions OBJECT-TYPE
    SYNTAX INTEGER (0..4294967295)
    ACCESS read-only
    STATUS mandatory
    DESCRIPTION
           "Maximum number of concurrent NetBIOS sessions
           configured for this port."
    ::= { lnNetbiosEntry 8 }

lnNBAvailCmdBlocks OBJECT-TYPE
    SYNTAX INTEGER (0..4294967295)
    ACCESS read-only
    STATUS mandatory
    DESCRIPTION
           "The number of NetBIOS command blocks which are
           currently available for use."
    ::= { lnNetbiosEntry 9 }

lnNBTotalCmdBlocks OBJECT-TYPE
    SYNTAX INTEGER (0..4294967295)
    ACCESS read-only
    STATUS mandatory
    DESCRIPTION
           "Maximum number of NetBIOS command blocks
           configured for this port."
    ::= { lnNetbiosEntry 10 }

lnNBPacketSize OBJECT-TYPE
    SYNTAX INTEGER (0..4294967295)
    ACCESS read-only
    STATUS mandatory
    DESCRIPTION
           "Packet size for this NetBIOS port (in bytes)."
    ::= { lnNetbiosEntry 11 }

lnNBReceivedPackets OBJECT-TYPE
    SYNTAX INTEGER (0..4294967295)
    ACCESS read-only
    STATUS mandatory
    DESCRIPTION
           "Total number of packets received by this port."
    ::= { lnNetbiosEntry 12 }

lnNBSentPackets OBJECT-TYPE
    SYNTAX INTEGER (0..4294967295)
    ACCESS read-only
    STATUS mandatory
    DESCRIPTION
           "Total number of packets sent from this port."
    ::= { lnNetbiosEntry 13 }

lnNBAbortedTransmissions OBJECT-TYPE
    SYNTAX INTEGER (0..4294967295)
    ACCESS read-only
    STATUS mandatory
    DESCRIPTION
           "Number of aborted transmissions for this port."
    ::= { lnNetbiosEntry 14 }

lnNBRetriedTransmissions OBJECT-TYPE
    SYNTAX INTEGER (0..4294967295)
    ACCESS read-only
    STATUS mandatory
    DESCRIPTION
           "Number of retried transmissions for this port."
    ::= { lnNetbiosEntry 15 }

lnNBAlignmentErrors OBJECT-TYPE
    SYNTAX INTEGER (0..4294967295)
    ACCESS read-only
    STATUS mandatory
    DESCRIPTION
           "Number of alignment errors for this port."
    ::= { lnNetbiosEntry 16 }

lnNBCollisionErrors OBJECT-TYPE
    SYNTAX INTEGER (0..4294967295)
    ACCESS read-only
    STATUS mandatory
    DESCRIPTION
           "Number of collision errors for this port."
    ::= { lnNetbiosEntry 17 }

lnNBCRCErrors OBJECT-TYPE
    SYNTAX INTEGER (0..4294967295)
    ACCESS read-only
    STATUS mandatory
    DESCRIPTION
           "Number of checksum errors for this port."
    ::= { lnNetbiosEntry 18 }

lnXPCTable OBJECT-TYPE
    SYNTAX SEQUENCE OF lnXPCEntry
    ACCESS not-accessible
    STATUS mandatory
    DESCRIPTION
           "A table containing one entry for each active
            XPC port on the server."
    ::= { lnComm 3 }

lnXPCEntry OBJECT-TYPE
    SYNTAX lnXPCEntry
    ACCESS not-accessible
    STATUS mandatory
    DESCRIPTION
           "The entry type definition for the lnXPCTable."
    INDEX { lnXPCIndex }
    ::= { lnXPCTable 1 }

lnXPCEntry ::= SEQUENCE {
    lnXPCIndex                  INTEGER,
    lnXPCPort                   DisplayString,
    lnXPCStatus                 DisplayString,
    lnXPCCarrierSpeed           INTEGER,
    lnXPCPortSpeed              INTEGER,
    lnXPCActiveSessions         INTEGER,
    lnXPCKiloBytesReceived      INTEGER,
    lnXPCKiloBytesSent          INTEGER,
    lnXPCMsgsReceived           INTEGER,
    lnXPCMsgsSent               INTEGER,
    lnXPCCRCErrors              INTEGER,
    lnXPCPortErrors             INTEGER,
    lnXPCRetransmissions        INTEGER
}

lnXPCIndex OBJECT-TYPE
    SYNTAX INTEGER (1..2147483647)
    ACCESS read-only
    STATUS mandatory
    DESCRIPTION
           "A unique value for each entry in the lnXPCTable."
    ::= { lnXPCEntry 1 }

lnXPCPort OBJECT-TYPE
    SYNTAX DisplayString
    ACCESS read-only
    STATUS mandatory
    DESCRIPTION
           "XPC port associated with this table entry."
    ::= { lnXPCEntry 2 }

lnXPCStatus OBJECT-TYPE
    SYNTAX DisplayString
    ACCESS read-only
    STATUS mandatory
    DESCRIPTION
           "The status of this XPC port."
    ::= { lnXPCEntry 3 }

lnXPCCarrierSpeed OBJECT-TYPE
    SYNTAX INTEGER (0..4294967295)
    ACCESS read-only
    STATUS mandatory
    DESCRIPTION
           "Communication speed (in bits per second) between
               local modem and remote modem."
    ::= { lnXPCEntry 4 }

lnXPCPortSpeed OBJECT-TYPE
    SYNTAX INTEGER (0..4294967295)
    ACCESS read-only
    STATUS mandatory
    DESCRIPTION
           "Communication speed (in bits per second) between
           server and local modem."
    ::= { lnXPCEntry 5 }

lnXPCActiveSessions OBJECT-TYPE
    SYNTAX INTEGER (0..4294967295)
    ACCESS read-only
    STATUS mandatory
    DESCRIPTION
           "Number of active user sessions on this XPC port."
    ::= { lnXPCEntry 6 }

lnXPCKiloBytesReceived OBJECT-TYPE
    SYNTAX INTEGER (0..4294967295)
    ACCESS read-only
    STATUS mandatory
    DESCRIPTION
           "Number of kilobytes received by this port."
    ::= { lnXPCEntry 7 }

lnXPCKiloBytesSent OBJECT-TYPE
    SYNTAX INTEGER (0..4294967295)
    ACCESS read-only
    STATUS mandatory
    DESCRIPTION
           "Number of kilobytes sent by this port."
    ::= { lnXPCEntry 8 }

lnXPCMsgsReceived OBJECT-TYPE
    SYNTAX INTEGER (0..4294967295)
    ACCESS read-only
    STATUS mandatory
    DESCRIPTION
           "Number of messages received by this port."
    ::= { lnXPCEntry 9 }

lnXPCMsgsSent OBJECT-TYPE
    SYNTAX INTEGER (0..4294967295)
    ACCESS read-only
    STATUS mandatory
    DESCRIPTION
           "Number of messages sent by this port."
    ::= { lnXPCEntry 10 }

lnXPCCRCErrors OBJECT-TYPE
    SYNTAX INTEGER (0..4294967295)
    ACCESS read-only
    STATUS mandatory
    DESCRIPTION
           "Number of checksum errors from this port."
    ::= { lnXPCEntry 11 }

lnXPCPortErrors OBJECT-TYPE
    SYNTAX INTEGER (0..4294967295)
    ACCESS read-only
    STATUS mandatory
    DESCRIPTION
           "Number of port errors."
    ::= { lnXPCEntry 12 }

lnXPCRetransmissions OBJECT-TYPE
    SYNTAX INTEGER (0..4294967295)
    ACCESS read-only
    STATUS mandatory
    DESCRIPTION
           "Number of retransmissions from this port."
    ::= { lnXPCEntry 13 }

lnAppleTalkStatsLogged OBJECT-TYPE
    SYNTAX INTEGER (0..4294967295)
    ACCESS read-only
    STATUS optional
    DESCRIPTION
           "Number of AppleTalk statistics logged by the Notes server."
    ::= { lnComm 4 }

lnNetWareSPXIIStatsLogged OBJECT-TYPE
    SYNTAX INTEGER (0..4294967295)
    ACCESS read-only
    STATUS optional
    DESCRIPTION
           "Number of NetWare SPX II statistics logged by the Notes server."
    ::= { lnComm 5 }

lnNetPortTable OBJECT-TYPE
    SYNTAX SEQUENCE OF lnNetPortEntry
    ACCESS not-accessible
    STATUS mandatory
    DESCRIPTION
           "A table containing one entry for each configured Notes network
            port on the server.  This table is new to the MIB as of Notes
            Release 4.  This table replaces most of the lnComm variables,
            remaining for backward compatibility, found in Release 3 of Notes."
    ::= { lnComm 6 }

lnNetPortEntry OBJECT-TYPE
    SYNTAX lnNetPortEntry
    ACCESS not-accessible
    STATUS mandatory
    DESCRIPTION
           "The entry type definition for the lnNetPortTable.
            This is specific to Notes Release 4."
    INDEX { lnNetPortIndex }
    ::= { lnNetPortTable 1 }

lnNetPortEntry ::= SEQUENCE {
    lnNetPortIndex         INTEGER,
    lnNetPortName          DisplayString,
    lnNetPortKBytesRec     INTEGER,
    lnNetPortKBytesSent    INTEGER,
    lnNetPortSessEstIn     INTEGER,
    lnNetPortSessEstOut    INTEGER,
    lnNetPortSessLimit     INTEGER,
    lnNetPortSessLimitMax  INTEGER,
    lnNetPortSessLimitMin  INTEGER,
    lnNetPortSessPeak      INTEGER,
    lnNetPortSessRecycled  INTEGER,
    lnNetPortSessRecycling INTEGER,
    lnSNARemoteLU          INTEGER,
    lnSNALocalLU           INTEGER,
    lnSNALNCVersion        INTEGER,
    lnSNAVersion           INTEGER,
    lnSNAMaxSessions       INTEGER,
    lnSNAActiveSessions    INTEGER,
    lnSNATPType            INTEGER,
    lnSNATPState           INTEGER,
    lnSNAConversationId    INTEGER,
    lnSNAMaxSendRUSize     INTEGER,
    lnSNAMaxRcvRUSize      INTEGER,
    lnSNASendPacingSize    INTEGER,
    lnSNARcvPacingSize     INTEGER,
    lnSNAPacingType        INTEGER,
    lnX25LocalResets       INTEGER,
    lnX25RemoteResets      INTEGER,
    lnX25WindowSize        INTEGER,
    lnX25FrameSize         INTEGER,
    lnX25PktSize           INTEGER,
    lnX25UnderRuns         INTEGER,
    lnX25OverRuns          INTEGER,
    lnX25REJTran           INTEGER,
    lnX25REJRcv            INTEGER,
    lnX25VCCfg             INTEGER,
    lnX25VCInUse           INTEGER,
    lnX25CRCErrors         INTEGER,
    lnX25LocalDTEAddress   INTEGER
    }

lnNetPortIndex OBJECT-TYPE
    SYNTAX INTEGER (1..2147483647)
    ACCESS read-only
    STATUS mandatory
    DESCRIPTION
        "A unique value for each entry in lnPortTable."
    ::= {lnNetPortEntry 1}

lnNetPortName OBJECT-TYPE
    SYNTAX DisplayString
    ACCESS read-only
    STATUS mandatory
    DESCRIPTION
        "The port name associate with this entry."
    ::= {lnNetPortEntry 2}

lnNetPortKBytesRec OBJECT-TYPE
    SYNTAX INTEGER (1..4294967295)
    ACCESS read-only
    STATUS mandatory
    DESCRIPTION
        "Total kilobytes received on this port.
         A value of zero may indicate the statistic's value is
         too large to be passed via SNMP."

    ::= {lnNetPortEntry 3}

lnNetPortKBytesSent OBJECT-TYPE
    SYNTAX INTEGER (1..4294967295)
    ACCESS read-only
    STATUS mandatory
    DESCRIPTION
        "Total kilobytes sent on this port.
         A value of zero may indicate the statistic's value is
         too large to be passed via SNMP."
    ::= {lnNetPortEntry 4}

lnNetPortSessEstIn OBJECT-TYPE
    SYNTAX INTEGER (1..4294967295)
    ACCESS read-only
    STATUS mandatory
    DESCRIPTION
        "The number of inbound sessions established on this port."
    ::= {lnNetPortEntry 5}

lnNetPortSessEstOut OBJECT-TYPE
    SYNTAX INTEGER (1..4294967295)
    ACCESS read-only
    STATUS mandatory
    DESCRIPTION
        "The number of outbound sessions established on this port."
    ::= {lnNetPortEntry 6}

lnNetPortSessLimit OBJECT-TYPE
    SYNTAX INTEGER (1..4294967295)
    ACCESS read-only
    STATUS mandatory
    DESCRIPTION
        "The current limit on the number of concurrent sessions on the port."
    ::= {lnNetPortEntry 7}

lnNetPortSessLimitMax OBJECT-TYPE
    SYNTAX INTEGER (1..4294967295)
    ACCESS read-only
    STATUS mandatory
    DESCRIPTION
        "Upward boundary of the range in which lnPortSessLimit may vary."
    ::= {lnNetPortEntry 8}

lnNetPortSessLimitMin OBJECT-TYPE
    SYNTAX INTEGER (1..4294967295)
    ACCESS read-only
    STATUS mandatory
    DESCRIPTION
        "Lower boundary of the range in which lnPortSessLimit may vary."
    ::= {lnNetPortEntry 9}

lnNetPortSessPeak OBJECT-TYPE
    SYNTAX INTEGER (1..4294967295)
    ACCESS read-only
    STATUS mandatory
    DESCRIPTION
        "The peak number of concurrent sessions on this port."
    ::= {lnNetPortEntry 10}

lnNetPortSessRecycled OBJECT-TYPE
    SYNTAX INTEGER (1..4294967295)
    ACCESS read-only
    STATUS mandatory
    DESCRIPTION
        "Number of dropped sessions due to low network resources."
    ::= {lnNetPortEntry 11}

lnNetPortSessRecycling OBJECT-TYPE
    SYNTAX INTEGER (1..4294967295)
    ACCESS read-only
    STATUS mandatory
    DESCRIPTION
         "Number of sessions currently being dropped due to low
          network resources."
    ::= {lnNetPortEntry 12}

lnSNARemoteLU OBJECT-TYPE
    SYNTAX INTEGER (1..4294967295)
    ACCESS read-only
    STATUS optional
    DESCRIPTION
         "Remote LU."
    ::= {lnNetPortEntry 13}

lnSNALocalLU OBJECT-TYPE
    SYNTAX INTEGER (1..4294967295)
    ACCESS read-only
    STATUS optional
    DESCRIPTION
         "Local LU."
    ::= {lnNetPortEntry 14}

lnSNALNCVersion OBJECT-TYPE
    SYNTAX INTEGER (1..4294967295)
    ACCESS read-only
    STATUS optional
    DESCRIPTION
         "SNA LNC Version."
    ::= {lnNetPortEntry 15}

lnSNAVersion OBJECT-TYPE
    SYNTAX INTEGER (1..4294967295)
    ACCESS read-only
    STATUS optional
    DESCRIPTION
         "SNA Version."
    ::= {lnNetPortEntry 16}

lnSNAMaxSessions OBJECT-TYPE
    SYNTAX INTEGER (1..4294967295)
    ACCESS read-only
    STATUS optional
    DESCRIPTION
         "Maximum number of SNA sessions that can exist."
    ::= {lnNetPortEntry 17}

lnSNAActiveSessions OBJECT-TYPE
    SYNTAX INTEGER (1..4294967295)
    ACCESS read-only
    STATUS optional
    DESCRIPTION
         "The total number of active SNA sessions."
    ::= {lnNetPortEntry 18}

lnSNATPType OBJECT-TYPE
    SYNTAX INTEGER (1..4294967295)
    ACCESS read-only
    STATUS optional
    DESCRIPTION
         "SNA transaction program type."
    ::= {lnNetPortEntry 19}

lnSNATPState OBJECT-TYPE
    SYNTAX INTEGER (1..4294967295)
    ACCESS read-only
    STATUS optional
    DESCRIPTION
         "SNA transaction program state."
    ::= {lnNetPortEntry 20}

lnSNAConversationId OBJECT-TYPE
    SYNTAX INTEGER (1..4294967295)
    ACCESS read-only
    STATUS optional
    DESCRIPTION
         "SNA conversation ID."
    ::= {lnNetPortEntry 21}

lnSNAMaxSendRUSize OBJECT-TYPE
    SYNTAX INTEGER (1..4294967295)
    ACCESS read-only
    STATUS optional
    DESCRIPTION
         "Maximum send request unit size sent."
    ::= {lnNetPortEntry 22}

lnSNAMaxRcvRUSize OBJECT-TYPE
    SYNTAX INTEGER (1..4294967295)
    ACCESS read-only
    STATUS optional
    DESCRIPTION
         "Maximum send request unit size received."
    ::= {lnNetPortEntry 23}

lnSNASendPacingSize OBJECT-TYPE
    SYNTAX INTEGER (1..4294967295)
    ACCESS read-only
    STATUS optional
    DESCRIPTION
         "The maximum number of outstanding request units which can
          be transmitted before receiving a pacing response from the
          remote LU."
    ::= {lnNetPortEntry 24}

lnSNARcvPacingSize OBJECT-TYPE
    SYNTAX INTEGER (1..4294967295)
    ACCESS read-only
    STATUS optional
    DESCRIPTION
         "The maximum number of oustanding request units which can
          be received before transmitting a pacing response to the
          remote LU."
    ::= {lnNetPortEntry 25}

lnSNAPacingType OBJECT-TYPE
    SYNTAX INTEGER (1..4294967295)
    ACCESS read-only
    STATUS optional
    DESCRIPTION
         "The SNA pacing size was originally determined at the creation
          of a session and remained constant through the life of the
          session.  More recent implementations allow the pacing size
          to dynamically change through the life of the session to increase
          efficiency and take advantage of available buffers.  This number
          represents the type of pacing done."
    ::= {lnNetPortEntry 26}

lnX25LocalResets OBJECT-TYPE
    SYNTAX INTEGER (1..4294967295)
    ACCESS read-only
    STATUS optional
    DESCRIPTION
         "The total number of local resets on this X25 port."
    ::= {lnNetPortEntry 27}

lnX25RemoteResets OBJECT-TYPE
    SYNTAX INTEGER (1..4294967295)
    ACCESS read-only
    STATUS optional
    DESCRIPTION
         "The total number of remote resets on this X25 port."
    ::= {lnNetPortEntry 28}

lnX25WindowSize OBJECT-TYPE
    SYNTAX INTEGER (1..4294967295)
    ACCESS read-only
    STATUS optional
    DESCRIPTION
         "The window size on this X25 port."
    ::= {lnNetPortEntry 29}

lnX25FrameSize OBJECT-TYPE
    SYNTAX INTEGER (1..4294967295)
    ACCESS read-only
    STATUS optional
    DESCRIPTION
         "The network frame size on this X25 port."
    ::= {lnNetPortEntry 30}

lnX25PktSize OBJECT-TYPE
    SYNTAX INTEGER (1..4294967295)
    ACCESS read-only
    STATUS optional
    DESCRIPTION
         "The network packet size on this X25 port."
    ::= {lnNetPortEntry 31}

lnX25UnderRuns OBJECT-TYPE
    SYNTAX INTEGER (1..4294967295)
    ACCESS read-only
    STATUS optional
    DESCRIPTION
         "This occurs when data is not given to the UART on an X.25 board
          fast enough for it to generate a complete packet on the wire."
    ::= {lnNetPortEntry 32}

lnX25OverRuns OBJECT-TYPE
    SYNTAX INTEGER (1..4294967295)
    ACCESS read-only
    STATUS optional
    DESCRIPTION
         "This occurs when data is given to the UART on an X.25 board
          faster than the board can generate packets to put on the wire."
    ::= {lnNetPortEntry 33}

lnX25REJTran OBJECT-TYPE
    SYNTAX INTEGER (1..4294967295)
    ACCESS read-only
    STATUS optional
    DESCRIPTION
         "The total number of REJs transmitted by this X25 port."
    ::= {lnNetPortEntry 34}

lnX25REJRcv OBJECT-TYPE
    SYNTAX INTEGER (1..4294967295)
    ACCESS read-only
    STATUS optional
    DESCRIPTION
         "The total number of REJs received by this X25 port."
    ::= {lnNetPortEntry 35}

lnX25VCCfg OBJECT-TYPE
    SYNTAX INTEGER (1..4294967295)
    ACCESS read-only
    STATUS optional
    DESCRIPTION
         "The total number of virtual circuits configured on this X25 port."
    ::= {lnNetPortEntry 36}

lnX25VCInUse OBJECT-TYPE
    SYNTAX INTEGER (1..4294967295)
    ACCESS read-only
    STATUS optional
    DESCRIPTION
    "The total number of virtual circuits currently in use on this X25 port."
    ::= {lnNetPortEntry 37}

lnX25CRCErrors OBJECT-TYPE
    SYNTAX INTEGER (1..4294967295)
    ACCESS read-only
    STATUS optional
    DESCRIPTION
         "The remote DTE address on this X25 port."
    ::= {lnNetPortEntry 38}

lnX25LocalDTEAddress OBJECT-TYPE
    SYNTAX INTEGER (1..4294967295)
    ACCESS read-only
    STATUS optional
    DESCRIPTION
         "The local DTE address on this X25 port."
    ::= {lnNetPortEntry 39}



--  ******************************************************************
--                         LNDISK GROUP
--  ******************************************************************

lnDiskFixed OBJECT-TYPE
    SYNTAX INTEGER (0..4294967295)
    ACCESS read-only
    STATUS mandatory
    DESCRIPTION
           "Number of fixed disks configured on this server."
    ::= { lnDisk 1 }

lnDiskFreeSwap OBJECT-TYPE
    SYNTAX INTEGER (0..4294967295)
    ACCESS read-only
    STATUS optional
    DESCRIPTION
           "Amount of free space left in swap area (in kilobytes)."
    ::= { lnDisk 2 }

lnDriveTable OBJECT-TYPE
    SYNTAX SEQUENCE OF lnDriveEntry
    ACCESS not-accessible
    STATUS mandatory
    DESCRIPTION
           "A table containing one entry for each disk (including
            network disks) configured on the server."
    ::= { lnDisk 3 }

lnDiskRemote OBJECT-TYPE
    SYNTAX INTEGER (0..4294967295)
    ACCESS read-only
    STATUS optional
    DESCRIPTION
           "The number of network disks or volumes mounted."
    ::= { lnDisk 4 }

lnDriveEntry OBJECT-TYPE
    SYNTAX lnDriveEntry
    ACCESS not-accessible
    STATUS mandatory
    DESCRIPTION
           "The entry type definition for the lnDriveTable."
    INDEX { lnDriveIndex }
    ::= { lnDriveTable 1 }

lnDriveEntry ::= SEQUENCE {
    lnDriveIndex        INTEGER,
    lnDriveLetter       DisplayString,
    lnDriveSize         INTEGER,
    lnDriveFree         INTEGER
}

lnDriveIndex OBJECT-TYPE
    SYNTAX INTEGER (1..2147483647)
    ACCESS read-only
    STATUS mandatory
    DESCRIPTION
           "A unique value for each entry in lnDriveTable."
    ::= { lnDriveEntry 1 }

lnDriveLetter OBJECT-TYPE
    SYNTAX DisplayString
    ACCESS read-only
    STATUS mandatory
    DESCRIPTION
           "The drive letter of the disk associated with this entry."
    ::= { lnDriveEntry 2 }

lnDriveSize OBJECT-TYPE
    SYNTAX INTEGER (0..4294967295)
    ACCESS read-only
    STATUS mandatory
    DESCRIPTION
           "The total size of this drive in kilobytes.
            A value of zero may indicate the statistic's value is
            too large to be passed via SNMP."
    ::= { lnDriveEntry 3 }

lnDriveFree OBJECT-TYPE
    SYNTAX INTEGER (0..4294967295)
    ACCESS read-only
    STATUS mandatory
    DESCRIPTION
           "The amount of free space left on this drive in kilobytes.
            A value of zero may indicate the statistic's value is
            too large to be passed via SNMP."
    ::= { lnDriveEntry 4 }

--  ******************************************************************
--                         LNMEM GROUP
--  ******************************************************************

lnMemAllocTotal OBJECT-TYPE
    SYNTAX INTEGER (0..4294967295)
    ACCESS read-only
    STATUS mandatory
    DESCRIPTION
           "Total memory allocated (should be sum of
                process and shared)."
    ::= { lnMem 1 }

lnMemAllocProcess OBJECT-TYPE
    SYNTAX INTEGER (0..4294967295)
    ACCESS read-only
    STATUS mandatory
    DESCRIPTION
           "Total process-private memory allocated by all
            currently-running processes."
    ::= { lnMem 2 }

lnMemAllocShared OBJECT-TYPE
    SYNTAX INTEGER (0..4294967295)
    ACCESS read-only
    STATUS mandatory
    DESCRIPTION
           "Total shared memory allocated."
    ::= { lnMem 3 }

lnMemAvailability OBJECT-TYPE
    SYNTAX DisplayString
    ACCESS read-only
    STATUS mandatory
    DESCRIPTION
           "Available memory on this server."
    ::= { lnMem 4 }

lnMemFree OBJECT-TYPE
    SYNTAX INTEGER (0..4294967295)
    ACCESS read-only
    STATUS mandatory
    DESCRIPTION
           "Total free memory, reported in kilobytes, as shown
            in the MEM.FREE Notes statistic.
            A value of zero may indicate the statistic's value is
            too large to be passed via SNMP."
    ::= { lnMem 5 }

lnMemSwapSize OBJECT-TYPE
    SYNTAX INTEGER (0..4294967295)
    ACCESS read-only
    STATUS optional
    DESCRIPTION
           "Size of swap file (NOTE:  this stat relies on the NOTES.INI
            variable 'SWAPPATH' if config.sys contains a swap
            path different from the default.)"
    ::= { lnMem 6 }

lnMemPhysicalRAM OBJECT-TYPE
    SYNTAX INTEGER (0..4294967295)
    ACCESS read-only
    STATUS optional
    DESCRIPTION
           "The total amount of physical memory on the server."
    ::= { lnMem 7 }


--  ******************************************************************
--                        LNDATABASE GROUP
--  ******************************************************************

lnDBBufferControlPoolSize OBJECT-TYPE
    SYNTAX INTEGER (0..4294967295)
    ACCESS read-only
    STATUS optional
    DESCRIPTION
           "Size of the buffer control pool."
    ::= { lnDatabase 1 }

lnDBBufferControlPoolUsed OBJECT-TYPE
    SYNTAX INTEGER (0..4294967295)
    ACCESS read-only
    STATUS optional
    DESCRIPTION
           "Number of bytes used in buffer control pool.
            A value of zero may indicate the statistic's value is
            too large to be passed via SNMP."
    ::= { lnDatabase 2 }

lnDBBufferPoolAllocated OBJECT-TYPE
    SYNTAX INTEGER (0..4294967295)
    ACCESS read-only
    STATUS optional
    DESCRIPTION
           "Number of bytes allocated from the buffer pool."
    ::= { lnDatabase 3 }

lnDBBufferPoolMaximum OBJECT-TYPE
    SYNTAX INTEGER (0..4294967295)
    ACCESS read-only
    STATUS optional
    DESCRIPTION
           "Maximum size of the buffer pool."
    ::= { lnDatabase 4 }

lnDBBufferPoolUsed OBJECT-TYPE
    SYNTAX INTEGER (0..4294967295)
    ACCESS read-only
    STATUS optional
    DESCRIPTION
           "Number of used buffers from the buffer pool."
    ::= { lnDatabase 5 }

lnDBNSFPoolSize OBJECT-TYPE
    SYNTAX INTEGER (0..4294967295)
    ACCESS read-only
    STATUS optional
    DESCRIPTION
           "Size of NSF pool."
    ::= { lnDatabase 6 }

lnDBNSFPoolUsed OBJECT-TYPE
    SYNTAX INTEGER (0..4294967295)
    ACCESS read-only
    STATUS optional
    DESCRIPTION
           "Amount of space used in NSF pool.
            A value of zero may indicate the statistic's value is
            too large to be passed via SNMP."
    ::= { lnDatabase 7 }

lnDBBufferPoolPercentReadsInBuffer OBJECT-TYPE
    SYNTAX INTEGER (0..4294967295)
    ACCESS read-only
    STATUS optional
    DESCRIPTION
           "Percentage of buffer pool reads."
    ::= { lnDatabase 8 }

lnDBBufferPoolReads OBJECT-TYPE
    SYNTAX INTEGER (0..4294967295)
    ACCESS read-only
    STATUS optional
    DESCRIPTION
           "Number of database buffer pool reads."
    ::= { lnDatabase 9 }

lnDBBufferPoolWrites OBJECT-TYPE
    SYNTAX INTEGER (0..4294967295)
    ACCESS read-only
    STATUS optional
    DESCRIPTION
           "Number of database buffer pool writes."
    ::= { lnDatabase 10 }

lnDBNIFPoolSize OBJECT-TYPE
    SYNTAX INTEGER (0..4294967295)
    ACCESS read-only
    STATUS optional
    DESCRIPTION
           "Size of database NIF pool."
    ::= { lnDatabase 11 }

lnDBNIFPoolUsed OBJECT-TYPE
    SYNTAX INTEGER (0..4294967295)
    ACCESS read-only
    STATUS optional
    DESCRIPTION
           "Number of database NIF pools.
            A value of zero may indicate the statistic's value is
            too large to be passed via SNMP."
    ::= { lnDatabase 12 }

lnDBNIFPoolPeak OBJECT-TYPE
    SYNTAX INTEGER (0..4294967295)
    ACCESS read-only
    STATUS optional
    DESCRIPTION
           "The peak number of database NIF pools.
            A value of zero may indicate the statistic's value is
            too large to be passed via SNMP."
    ::= { lnDatabase 13 }

lnDBNSFPoolPeak OBJECT-TYPE
    SYNTAX INTEGER (0..4294967295)
    ACCESS read-only
    STATUS optional
    DESCRIPTION
           "The peak number of database NSF pools.
            A value of zero may indicate the statistic's value is
            too large to be passed via SNMP."
    ::= { lnDatabase 14 }

lnDBCacheCurrentEntries OBJECT-TYPE
    SYNTAX INTEGER (0..4294967295)
    ACCESS read-only
    STATUS optional
    DESCRIPTION
           "The number of databases currently in the cache.  Administrators
            should monitor this number to see whether it approaches the
            NSF_DBCACHE_MAXENTRIES setting.  If it does, this indicates
            the cache is under pressure.  If this situation
            occurs frequently, the administrator should increase the setting for
            NSF_DBCACHE_MAXENTRIES."
    ::= { lnDatabase 15 }

lnDBCacheHighWaterMark OBJECT-TYPE
    SYNTAX INTEGER (0..4294967295)
    ACCESS read-only
    STATUS optional
    DESCRIPTION
           "The maximum number of databases in the cache during this
            running of the Domino server program.  Note that this number
            may be artificially high due to startup activity, so it may
            be of limited use as a genuine indicator of cache performance."
    ::= { lnDatabase 16 }

lnDBCacheHits OBJECT-TYPE
    SYNTAX INTEGER (0..4294967295)
    ACCESS read-only
    STATUS optional
    DESCRIPTION
           "The number of times an lnDBCacheInitialDbOpen is satisfied by
            finding a database in the cache.  A high 'hits-to-opens' ratio
            indicates the database cache is working effectively, since
            most users are opening databases in the cache without having
            to wait for the usual time required by an initial (non-cache)
            open.  If the ratio is low (in other words, more users are
            having to wait for databases not in the cache to open), the
            administrator can increase the NSF_DBCACHE_MAXENTRIES
            settings."
    ::= { lnDatabase 17 }

lnDBCacheInitialDbOpens OBJECT-TYPE
    SYNTAX INTEGER (0..4294967295)
    ACCESS read-only
    STATUS optional
    DESCRIPTION
           "The number of times a user/server opened a database that was
            not already being used by another user/server.  By comparing
            this number to lnDBCacheHits, administrators can gauge the
            effectiveness of the cache."
    ::= { lnDatabase 18 }

lnDBCacheLookups OBJECT-TYPE
    SYNTAX INTEGER (0..4294967295)
    ACCESS read-only
    STATUS optional
    DESCRIPTION
           "The number of lookups performed on the cache."
    ::= { lnDatabase 19 }

lnDBCacheMaxEntries OBJECT-TYPE
    SYNTAX INTEGER (0..4294967295)
    ACCESS read-only
    STATUS optional
    DESCRIPTION
           "The number of databases that the server can currently
            hold in its cache at once."
    ::= { lnDatabase 20 }

lnDBCacheOvercrowdingRejections OBJECT-TYPE
    SYNTAX INTEGER (0..4294967295)
    ACCESS read-only
    STATUS optional
    DESCRIPTION
           "The number of times a database is not placed into the
            cache when it is closed because lnDBCacheCurrentEntries equals
            or exceeds lnDBCacheMaxEntries*1.5.  This number should stay
            low.  If it begins to rise, you should increase the
            NSF_DbCache_Maxentries settings."
    ::= { lnDatabase 21 }

lnDBBufferControlPoolPeak OBJECT-TYPE
    SYNTAX INTEGER (0..4294967295)
    ACCESS read-only
    STATUS optional
    DESCRIPTION
           "The peak size of buffer control pool.
            A value of zero may indicate the statistic's value is
            too large to be passed via SNMP."
    ::= { lnDatabase 22 }


--  ******************************************************************
--                          LNAGENT GROUP
--  ******************************************************************

lnDailyAccessDenials OBJECT-TYPE
    SYNTAX INTEGER (0..4294967295)
    ACCESS read-only
    STATUS optional
    DESCRIPTION
           "The number of times the agent manager failed to execute
            a given task, probably due to ACL restrictions."
    ::= { lnAgentMgr 1 }

lnDailyScheduledRuns OBJECT-TYPE
    SYNTAX INTEGER (0..4294967295)
    ACCESS read-only
    STATUS optional
    DESCRIPTION
           "The number of tasks that the agent manager has scheduled
            to run during the course of the day."
    ::= { lnAgentMgr 2 }

lnDailyTriggeredRuns OBJECT-TYPE
    SYNTAX INTEGER (0..4294967295)
    ACCESS read-only
    STATUS optional
    DESCRIPTION
           "The number of tasks that the agent manager has had triggered
            to run by an event during the course of the day."
    ::= { lnAgentMgr 3 }

lnDailyUnsuccessfulRuns OBJECT-TYPE
    SYNTAX INTEGER (0..4294967295)
    ACCESS read-only
    STATUS optional
    DESCRIPTION
           "The number of tasks the agent manager has unsuccessfully
            run during the course of the day."
    ::= { lnAgentMgr 4 }

lnDailyUsedRunTime OBJECT-TYPE
    SYNTAX DisplayString
    ACCESS read-only
    STATUS optional
    DESCRIPTION
          "The number of seconds used to run an agent."
    ::= { lnAgentMgr 5 }

lnHourlyAccessDenials OBJECT-TYPE
    SYNTAX INTEGER (0..4294967295)
    ACCESS read-only
    STATUS optional
    DESCRIPTION
           "The number of tasks that the agent manager failed to
            execute during the last hour, probably due to ACL restrictions."
    ::= { lnAgentMgr 6 }

lnHourlyScheduledRuns OBJECT-TYPE
    SYNTAX INTEGER (0..4294967295)
    ACCESS read-only
    STATUS optional
    DESCRIPTION
           "The number of tasks the agent manager has scheduled to
            run during the last hour."
    ::= { lnAgentMgr 7 }

lnHourlyTriggeredRuns OBJECT-TYPE
    SYNTAX INTEGER (0..4294967295)
    ACCESS read-only
    STATUS optional
    DESCRIPTION
           "The number of tasks the agent manager has had triggered to
            run by an event during the last hour."
    ::= { lnAgentMgr 8 }

lnHourlyUnsuccessfulRuns OBJECT-TYPE
    SYNTAX INTEGER (0..4294967295)
    ACCESS read-only
    STATUS optional
    DESCRIPTION
           "The number of tasks the agent manager has unsuccessfully
            run during the last hour."
    ::= { lnAgentMgr 9 }

lnHourlyUsedRunTime OBJECT-TYPE
    SYNTAX DisplayString
    ACCESS read-only
    STATUS optional
    DESCRIPTION
            "The number of seconds to run an agent."
    ::= { lnAgentMgr 10 }

--  ******************************************************************
--                      lnMTA GROUP
--  ******************************************************************

lnMTATable OBJECT-TYPE
    SYNTAX SEQUENCE OF lnMTAEntry
    ACCESS not-accessible
    STATUS mandatory
    DESCRIPTION
           "A table containing one entry for each running
            Notes server MTA."
    ::= { lnMTA 1 }

lnMTAEntry OBJECT-TYPE
    SYNTAX lnMTAEntry
    ACCESS not-accessible
    STATUS mandatory
    DESCRIPTION
           "The entry type definition for the lnMTATable."
    INDEX { lnMTAIndex }
    ::= { lnMTATable 1 }

lnMTAEntry ::= SEQUENCE {
    lnMTAIndex              INTEGER,
    lnMTAName               DisplayString,
    lnMTADeadMsgs           INTEGER,
    lnMTAWaitingRecp        INTEGER,
    lnMTAWaitingMsgs        INTEGER,
    lnMTATransferFailures   INTEGER,
    lnMTATotalKBTransferred INTEGER,
    lnMTATransferredMsgs    INTEGER,
    lnMTATotalRouted        INTEGER
    }

lnMTAIndex OBJECT-TYPE
    SYNTAX INTEGER (1..2147483647)
    ACCESS read-only
    STATUS mandatory
    DESCRIPTION
           "A unique value for each MTA running on the Notes server."
    ::= { lnMTAEntry 1 }

lnMTAName OBJECT-TYPE
    SYNTAX DisplayString
    ACCESS read-only
    STATUS mandatory
    DESCRIPTION
           "A string representing the name of a MTA running on
                the Notes server."
    ::= { lnMTAEntry 2 }

lnMTADeadMsgs OBJECT-TYPE
    SYNTAX INTEGER (0..4294967295)
    ACCESS read-only
    STATUS optional
    DESCRIPTION
          "The number of dead mail messages.  (Messages that are stuck
           in the MTA queue.)"
    ::= { lnMTAEntry 3 }

lnMTAWaitingRecp OBJECT-TYPE
    SYNTAX INTEGER (0..4294967295)
    ACCESS read-only
    STATUS optional
    DESCRIPTION
           "The number of recipients for pending mail.  (The number of
            recipients responsible for lnMTAWaitingMsgs.)"
    ::= { lnMTAEntry 4 }

lnMTAWaitingMsgs OBJECT-TYPE
    SYNTAX INTEGER (0..4294967295)
    ACCESS read-only
    STATUS optional
    DESCRIPTION
           "The amount of mail awaiting routing.  (The number of messages
            that are in the process of being routed.)"
    ::= { lnMTAEntry 5 }

lnMTATransferFailures OBJECT-TYPE
    SYNTAX INTEGER (0..4294967295)
    ACCESS read-only
    STATUS optional
    DESCRIPTION
           "The number of messages the MTA could not transfer."
    ::= { lnMTAEntry 6 }

lnMTATotalKBTransferred OBJECT-TYPE
    SYNTAX INTEGER (0..4294967295)
    ACCESS read-only
    STATUS optional
    DESCRIPTION
           "The total number of kilobyte transferred outbound
            or into any of the .box's by this MTA."
    ::= { lnMTAEntry 7 }

lnMTATransferredMsgs OBJECT-TYPE
    SYNTAX INTEGER (0..4294967295)
    ACCESS read-only
    STATUS optional
    DESCRIPTION
           "The total number of messages transferred outbound or
            into any of the .box's by this MTA."
    ::= { lnMTAEntry 8 }

lnMTATotalRouted OBJECT-TYPE
    SYNTAX INTEGER (0..4294967295)
    ACCESS read-only
    STATUS optional
    DESCRIPTION
           "The total amount of mail routed (# of recipients routed to)
            outbound or into any of the .box's."
    ::= { lnMTAEntry 9 }

--  ******************************************************************
--                      lnWeb GROUP
--  ******************************************************************

lnWebAccessFtp OBJECT-TYPE
   SYNTAX INTEGER (0..429496795)
   ACCESS read-only
   STATUS optional
   DESCRIPTION
        "The number of FTP connections on this Web server."
   ::= { lnWeb 1}

lnWebAccessGopher OBJECT-TYPE
   SYNTAX INTEGER (0..429496795)
   ACCESS read-only
   STATUS optional
   DESCRIPTION
        "The number of Gopher connections on this Web server."
   ::= { lnWeb 2}

lnWebAccessHttp OBJECT-TYPE
   SYNTAX INTEGER (0..429496795)
   ACCESS read-only
   STATUS optional
   DESCRIPTION
        "The number of HTTP connections on this Web server."
   ::= { lnWeb 3}

lnWebKBytesReceived OBJECT-TYPE
   SYNTAX INTEGER (0..429496795)
   ACCESS read-only
   STATUS optional
   DESCRIPTION
        "Total kilobytes received by this Web server."
   ::= { lnWeb 4}

lnWebKBytesSent OBJECT-TYPE
   SYNTAX INTEGER (0..429496795)
   ACCESS read-only
   STATUS optional
   DESCRIPTION
        "Total kilobytes sent by this Web server."
   ::= { lnWeb 5}

lnWebImageCacheHits OBJECT-TYPE
   SYNTAX INTEGER (0..429496795)
   ACCESS read-only
   STATUS optional
   DESCRIPTION
        "The number of successful hits on the image cache."
   ::= { lnWeb 6}

lnWebImageCacheMisses OBJECT-TYPE
   SYNTAX INTEGER (0..429496795)
   ACCESS read-only
   STATUS optional
   DESCRIPTION
        "The number of image cache misses."
   ::= { lnWeb 7}

lnWebLogMessages OBJECT-TYPE
   SYNTAX DisplayString
   ACCESS read-only
   STATUS optional
   DESCRIPTION
        " 'Yes' if message logging is turned on."
   ::= { lnWeb 8}

lnWebActiveProcesses OBJECT-TYPE
   SYNTAX INTEGER (0..429496795)
   ACCESS read-only
   STATUS optional
   DESCRIPTION
        "The number of active Web Retriever processes."
   ::= { lnWeb 9}

lnWebBusyProcesses OBJECT-TYPE
   SYNTAX INTEGER (0..429496795)
   ACCESS read-only
   STATUS optional
   DESCRIPTION
        "The number of Web Retriever processes currently busy working."
   ::= { lnWeb 10}

lnWebIdleProcesses OBJECT-TYPE
   SYNTAX INTEGER (0..429496795)
   ACCESS read-only
   STATUS optional
   DESCRIPTION
        "The number of Web Retriever processes that are sitting idle."
   ::= { lnWeb 11}

lnWebMaxProcesses OBJECT-TYPE
   SYNTAX INTEGER (0..429496795)
   ACCESS read-only
   STATUS optional
   DESCRIPTION
   "The maximum number of Web Retriever processes allowable on this server."
   ::= { lnWeb 12}

lnWebProcessState OBJECT-TYPE
   SYNTAX DisplayString
   ACCESS read-only
   STATUS optional
   DESCRIPTION
        "The number of image cache misses."
   ::= { lnWeb 13}

lnWebTimeCurrent OBJECT-TYPE
   SYNTAX DisplayString
   ACCESS read-only
   STATUS optional
   DESCRIPTION
        "The current time, as set on this Web Retriever."
   ::= { lnWeb 14}

lnWebTimeDuration OBJECT-TYPE
   SYNTAX DisplayString
   ACCESS read-only
   STATUS optional
   DESCRIPTION
        "Shows the amount of time this Web Retriever has been running."
   ::= { lnWeb 15}

lnWebTimeStart OBJECT-TYPE
   SYNTAX DisplayString
   ACCESS read-only
   STATUS optional
   DESCRIPTION
        "The time the Web Retriever processes started."
   ::= { lnWeb 16}

lnWebUrlFail OBJECT-TYPE
   SYNTAX INTEGER (0..429496795)
   ACCESS read-only
   STATUS optional
   DESCRIPTION
        "The number URL requests that have failed on this Web Retriever."
   ::= { lnWeb 17}

lnWebUrlRequested OBJECT-TYPE
   SYNTAX INTEGER (0..429496795)
   ACCESS read-only
   STATUS optional
   DESCRIPTION
        "The total number of URL requests on this Web Retriever."
   ::= { lnWeb 18}

lnWebUrlSucceeded OBJECT-TYPE
   SYNTAX INTEGER (0..429496795)
   ACCESS read-only
   STATUS optional
   DESCRIPTION
        "The number of URL requests successfully completed on this server."
   ::= { lnWeb 19}

lnWebRetrieverVersion OBJECT-TYPE
   SYNTAX DisplayString
   ACCESS read-only
   STATUS optional
   DESCRIPTION
        "The version of the Web Retriever software that is running."
   ::= { lnWeb 20}

lnWebVpoolMaxBuf OBJECT-TYPE
   SYNTAX INTEGER (0..429496795)
   ACCESS read-only
   STATUS optional
   DESCRIPTION
         "The number of buffer VPOOLs which have reached maximum size."
   ::= { lnWeb 21}

lnWebVpoolMaxElement OBJECT-TYPE
   SYNTAX INTEGER (0..429496795)
   ACCESS read-only
   STATUS optional
   DESCRIPTION
         "The number of element VPOOLs which have reached maximum size."
   ::= { lnWeb 22}

lnWebVpoolMaxMarker OBJECT-TYPE
   SYNTAX INTEGER (0..429496795)
   ACCESS read-only
   STATUS optional
   DESCRIPTION
         "The number of marker VPOOLs which have reached maximum size."
   ::= { lnWeb 23}

lnWebVpoolMaxText OBJECT-TYPE
   SYNTAX INTEGER (0..429496795)
   ACCESS read-only
   STATUS optional
   DESCRIPTION
         "The number of text VPOOLs which have reached maximum size."
   ::= { lnWeb 24}

lnWebVpoolMaxUrl OBJECT-TYPE
   SYNTAX INTEGER (0..429496795)
   ACCESS read-only
   STATUS optional
   DESCRIPTION
         "The number of URL VPOOLs which have reached maximum size."
   ::= { lnWeb 25}

lnWebProcessTable OBJECT-TYPE
   SYNTAX SEQUENCE OF lnWebProcEntry
   ACCESS not-accessible
   STATUS optional
   DESCRIPTION
        "This table will show statistics for all Web Retriever
         processes on the server."
   ::= { lnWeb 26}

lnWebProcEntry OBJECT-TYPE
    SYNTAX lnWebProcEntry
    ACCESS not-accessible
    STATUS optional
    DESCRIPTION
      "This defines the MIB variables specific to each Web Retriever process."
    INDEX { lnWebProcIndex }
    ::= { lnWebProcessTable 1 }

lnWebProcEntry ::= SEQUENCE {
    lnWebProcIndex           INTEGER,
    lnWebProcNumber          DisplayString,
    lnWebProcAccFtp          INTEGER,
    lnWebProcAccGopher       INTEGER,
    lnWebProcAccHttp         INTEGER,
    lnWebProcKBytesRec       INTEGER,
    lnWebProcKBytesSent      INTEGER,
    lnWebProcCacheHits       INTEGER,
    lnWebProcCacheMisses     INTEGER,
    lnWebProcPid             INTEGER,
    lnWebProcUrlFail         INTEGER,
    lnWebProcUrlReq          INTEGER,
    lnWebProcUrlSucc         INTEGER,
    lnWebProcVpoolCurBuf     INTEGER,
    lnWebProcVpoolCurElement INTEGER,
    lnWebProcVpoolCurMarker  INTEGER,
    lnWebProcVpoolCurText    INTEGER,
    lnWebProcVpoolCurUrl     INTEGER,
    lnWebProcVpoolMaxBuf     INTEGER,
    lnWebProcVpoolMaxElement INTEGER,
    lnWebProcVpoolMaxMarker  INTEGER,
    lnWebProcVpoolMaxText    INTEGER,
    lnWebProcVpoolMaxUrl     INTEGER
    }

lnWebProcIndex OBJECT-TYPE
   SYNTAX INTEGER (0..429496795)
   ACCESS read-only
   STATUS mandatory
   DESCRIPTION
        "A unique index entry for each Web Retriever process."
   ::= { lnWebProcEntry 1}

lnWebProcNumber OBJECT-TYPE
   SYNTAX DisplayString
   ACCESS read-only
   STATUS mandatory
   DESCRIPTION
        "The number associated with the Web Retriever process in
         the Notes stats structure."
   ::= { lnWebProcEntry 2}

lnWebProcAccFtp OBJECT-TYPE
   SYNTAX INTEGER (0..429496795)
   ACCESS read-only
   STATUS mandatory
   DESCRIPTION
        "The number of FTP connections this Web Retriever process is handling."
   ::= { lnWebProcEntry 3}

lnWebProcAccGopher OBJECT-TYPE
   SYNTAX INTEGER (0..429496795)
   ACCESS read-only
   STATUS mandatory
   DESCRIPTION
        "The number of Gopher connections this Web Retriever
             process     is handling."
   ::= { lnWebProcEntry 4}

lnWebProcAccHttp OBJECT-TYPE
   SYNTAX INTEGER (0..429496795)
   ACCESS read-only
   STATUS mandatory
   DESCRIPTION
        "The number of HTTP connections this Web Retriever
             process     is handling."
   ::= { lnWebProcEntry 5}

lnWebProcKBytesRec OBJECT-TYPE
   SYNTAX INTEGER (0..429496795)
   ACCESS read-only
   STATUS mandatory
   DESCRIPTION
        "The total number of kilobytes this Web Retriever process has received."
   ::= { lnWebProcEntry 6}

lnWebProcKBytesSent OBJECT-TYPE
   SYNTAX INTEGER (0..429496795)
   ACCESS read-only
   STATUS mandatory
   DESCRIPTION
        "The total number of kilobytes this Web Retriever process has sent."
   ::= { lnWebProcEntry 7}

lnWebProcCacheHits OBJECT-TYPE
   SYNTAX INTEGER (0..429496795)
   ACCESS read-only
   STATUS mandatory
   DESCRIPTION
        "The total number of successful image cache hits for
         this Web Retriever."
   ::= { lnWebProcEntry 8}

lnWebProcCacheMisses OBJECT-TYPE
   SYNTAX INTEGER (0..429496795)
   ACCESS read-only
   STATUS mandatory
   DESCRIPTION
        "The total number of image cache misses for
         this Web Retriever."
   ::= { lnWebProcEntry 9}

lnWebProcPid OBJECT-TYPE
   SYNTAX INTEGER (0..429496795)
   ACCESS read-only
   STATUS mandatory
   DESCRIPTION
        "The process ID associated with this Web Retriever process."
   ::= { lnWebProcEntry 10}

lnWebProcUrlFail OBJECT-TYPE
   SYNTAX INTEGER (0..429496795)
   ACCESS read-only
   STATUS mandatory
   DESCRIPTION
        "The number of URL opens that failed for this Web Retriever process."
   ::= { lnWebProcEntry 11}

lnWebProcUrlReq OBJECT-TYPE
   SYNTAX INTEGER (0..429496795)
   ACCESS read-only
   STATUS mandatory
   DESCRIPTION
        "The number of URL open requests this Web Retriever process handled."
   ::= { lnWebProcEntry 12}

lnWebProcUrlSucc OBJECT-TYPE
   SYNTAX INTEGER (0..429496795)
   ACCESS read-only
   STATUS mandatory
   DESCRIPTION
        "The number of successful URL opens this Web Retriever process handled."
   ::= { lnWebProcEntry 13}

lnWebProcVpoolCurBuf OBJECT-TYPE
   SYNTAX INTEGER (0..429496795)
   ACCESS read-only
   STATUS mandatory
   DESCRIPTION
     "The number of buffer VPOOLs currently allocated for this Web Retriever process."
   ::= { lnWebProcEntry 14}

lnWebProcVpoolCurElement OBJECT-TYPE
   SYNTAX INTEGER (0..429496795)
   ACCESS read-only
   STATUS mandatory
   DESCRIPTION
     "The number of element VPOOLs currently allocated for this Web Retriever process."
   ::= { lnWebProcEntry 15}

lnWebProcVpoolCurMarker OBJECT-TYPE
   SYNTAX INTEGER (0..429496795)
   ACCESS read-only
   STATUS mandatory
   DESCRIPTION
     "The number of marker VPOOLs currently allocated for this Web Retriever process."
   ::= { lnWebProcEntry 16}

lnWebProcVpoolCurText OBJECT-TYPE
   SYNTAX INTEGER (0..429496795)
   ACCESS read-only
   STATUS mandatory
   DESCRIPTION
     "The number of text VPOOLs currently allocated for this Web Retriever process."
   ::= { lnWebProcEntry 17}

lnWebProcVpoolCurUrl OBJECT-TYPE
   SYNTAX INTEGER (0..429496795)
   ACCESS read-only
   STATUS mandatory
   DESCRIPTION
     "The number of URL VPOOLs currently allocated for this Web Retriever process."
   ::= { lnWebProcEntry 18}

lnWebProcVpoolMaxBuf OBJECT-TYPE
   SYNTAX INTEGER (0..429496795)
   ACCESS read-only
   STATUS mandatory
   DESCRIPTION
     "The number of buffer VPOOLs allocated for this Web Retriever process
      that have reached their maximum size."
   ::= { lnWebProcEntry 19}

lnWebProcVpoolMaxElement OBJECT-TYPE
   SYNTAX INTEGER (0..429496795)
   ACCESS read-only
   STATUS mandatory
   DESCRIPTION
     "The number of element VPOOLs allocated to this Web Retriever process
      that have reached their maximum size."
   ::= { lnWebProcEntry 20}

lnWebProcVpoolMaxMarker OBJECT-TYPE
   SYNTAX INTEGER (0..429496795)
   ACCESS read-only
   STATUS mandatory
   DESCRIPTION
     "The number of VPOOLs allocated to this Web Retriever process
      that have reached their maximum size."
   ::= { lnWebProcEntry 21}

lnWebProcVpoolMaxText OBJECT-TYPE
   SYNTAX INTEGER (0..429496795)
   ACCESS read-only
   STATUS mandatory
   DESCRIPTION
     "The number of text VPOOLs allocated to this Web Retriever process
      that have reached their maximum size."
   ::= { lnWebProcEntry 22}

lnWebProcVpoolMaxUrl OBJECT-TYPE
   SYNTAX INTEGER (0..429496795)
   ACCESS read-only
   STATUS mandatory
   DESCRIPTION
     "The number of URL VPOOLs allocated to this Web Retriever process
      that have reached their maximum size."
   ::= { lnWebProcEntry 23}


--  ******************************************************************
--                      LNOBJECT GROUP (SCOS stats)
--  ******************************************************************

lnObjectFileName OBJECT-TYPE
   SYNTAX DisplayString
   ACCESS read-only
   STATUS optional
   DESCRIPTION
        "The name of the primary single-copy object store (SCOS) database
         currently in use."
   ::= { lnObject 1}

lnObjectTable OBJECT-TYPE
   SYNTAX SEQUENCE OF lnObjectEntry
   ACCESS not-accessible
   STATUS optional
   DESCRIPTION
        "This table describes statistics for the single-copy object store
         of each SCOS database that is currently being accessed."
   ::= { lnObject 2}

lnObjectEntry OBJECT-TYPE
   SYNTAX lnObjectEntry
   ACCESS not-accessible
   STATUS mandatory
   DESCRIPTION
       "All items in LnObjectTable."
   ::= { lnObjectTable 1 }

lnObjectEntry ::= SEQUENCE {
   lnObjectIndex INTEGER,
   lnObjectName DisplayString,
   lnObjectSharedBy01 INTEGER,
   lnObjectSharedBy02 INTEGER,
   lnObjectSharedBy03 INTEGER,
   lnObjectSharedBy04 INTEGER,
   lnObjectSharedBy05 INTEGER,
   lnObjectSharedBy06 INTEGER,
   lnObjectSharedBy07 INTEGER,
   lnObjectSharedBy08 INTEGER,
   lnObjectSharedBy09 INTEGER,
   lnObjectSharedBy10 INTEGER,
   lnObjectSharedBy11 INTEGER,
   lnObjectSharedBy12 INTEGER,
   lnObjectSharedBy13 INTEGER,
   lnObjectSharedBy14 INTEGER,
   lnObjectSharedBy15 INTEGER,
   lnObjectSharedBy16 INTEGER,
   lnObjectSharedBy17 INTEGER,
   lnObjectSharedBy18 INTEGER,
   lnObjectSharedBy19 INTEGER,
   lnObjectSharedBy20 INTEGER,
   lnObjectSharedByGreater INTEGER,
   lnObjectSharedByTotal INTEGER
}

lnObjectIndex OBJECT-TYPE
   SYNTAX INTEGER (1..429496795)
   ACCESS read-only
   STATUS optional
   DESCRIPTION
      "An internal index for each SCOS database in use."
   ::= {lnObjectEntry 1}

lnObjectName OBJECT-TYPE
   SYNTAX DisplayString
   ACCESS read-only
   STATUS optional
   DESCRIPTION
      "The name of the single copy object store database."
   ::= {lnObjectEntry 2}

lnObjectSharedBy01 OBJECT-TYPE
   SYNTAX INTEGER (1..429496795)
   ACCESS read-only
   STATUS optional
   DESCRIPTION
      "Messages with 1 pointer."
   ::= {lnObjectEntry 3}

lnObjectSharedBy02 OBJECT-TYPE
   SYNTAX INTEGER (1..429496795)
   ACCESS read-only
   STATUS optional
   DESCRIPTION
      "Messages with 2 pointers."
   ::= {lnObjectEntry 4}

lnObjectSharedBy03 OBJECT-TYPE
   SYNTAX INTEGER (1..429496795)
   ACCESS read-only
   STATUS optional
   DESCRIPTION
      "Messages with 3 pointers."
   ::= {lnObjectEntry 5}

lnObjectSharedBy04 OBJECT-TYPE
   SYNTAX INTEGER (1..429496795)
   ACCESS read-only
   STATUS optional
   DESCRIPTION
      "Messages with 4 pointers."
   ::= {lnObjectEntry 6}

lnObjectSharedBy05 OBJECT-TYPE
   SYNTAX INTEGER (1..429496795)
   ACCESS read-only
   STATUS optional
   DESCRIPTION
      "Messages with 5 pointers."
   ::= {lnObjectEntry 7}

lnObjectSharedBy06 OBJECT-TYPE
   SYNTAX INTEGER (1..429496795)
   ACCESS read-only
   STATUS optional
   DESCRIPTION
      "Messages with 6 pointers."
   ::= {lnObjectEntry 8}

lnObjectSharedBy07 OBJECT-TYPE
   SYNTAX INTEGER (1..429496795)
   ACCESS read-only
   STATUS optional
   DESCRIPTION
      "Messages with 7 pointers."
   ::= {lnObjectEntry 9}

lnObjectSharedBy08 OBJECT-TYPE
   SYNTAX INTEGER (1..429496795)
   ACCESS read-only
   STATUS optional
   DESCRIPTION
      "Messages with 8 pointers."
   ::= {lnObjectEntry 10}

lnObjectSharedBy09 OBJECT-TYPE
   SYNTAX INTEGER (1..429496795)
   ACCESS read-only
   STATUS optional
   DESCRIPTION
      "Messages with 9 pointers."
   ::= {lnObjectEntry 11}

lnObjectSharedBy10 OBJECT-TYPE
   SYNTAX INTEGER (1..429496795)
   ACCESS read-only
   STATUS optional
   DESCRIPTION
      "Messages with 10 pointers."
   ::= {lnObjectEntry 12}

lnObjectSharedBy11 OBJECT-TYPE
   SYNTAX INTEGER (1..429496795)
   ACCESS read-only
   STATUS optional
   DESCRIPTION
      "Messages with 11 pointers."
   ::= {lnObjectEntry 13}

lnObjectSharedBy12 OBJECT-TYPE
   SYNTAX INTEGER (1..429496795)
   ACCESS read-only
   STATUS optional
   DESCRIPTION
      "Messages with 12 pointers."
   ::= {lnObjectEntry 14}

lnObjectSharedBy13 OBJECT-TYPE
   SYNTAX INTEGER (1..429496795)
   ACCESS read-only
   STATUS optional
   DESCRIPTION
      "Messages with 13 pointers."
   ::= {lnObjectEntry 15}

lnObjectSharedBy14 OBJECT-TYPE
   SYNTAX INTEGER (1..429496795)
   ACCESS read-only
   STATUS optional
   DESCRIPTION
      "Messages with 14 pointers."
   ::= {lnObjectEntry 16}

lnObjectSharedBy15 OBJECT-TYPE
   SYNTAX INTEGER (1..429496795)
   ACCESS read-only
   STATUS optional
   DESCRIPTION
      "Messages with 15 pointers."
   ::= {lnObjectEntry 17}

lnObjectSharedBy16 OBJECT-TYPE
   SYNTAX INTEGER (1..429496795)
   ACCESS read-only
   STATUS optional
   DESCRIPTION
      "Messages with 16 pointers."
   ::= {lnObjectEntry 18}

lnObjectSharedBy17 OBJECT-TYPE
   SYNTAX INTEGER (1..429496795)
   ACCESS read-only
   STATUS optional
   DESCRIPTION
      "Messages with 17 pointers."
   ::= {lnObjectEntry 19}

lnObjectSharedBy18 OBJECT-TYPE
   SYNTAX INTEGER (1..429496795)
   ACCESS read-only
   STATUS optional
   DESCRIPTION
      "Messages with 18 pointers."
   ::= {lnObjectEntry 20}

lnObjectSharedBy19 OBJECT-TYPE
   SYNTAX INTEGER (1..429496795)
   ACCESS read-only
   STATUS optional
   DESCRIPTION
      "Messages with 19 pointers."
   ::= {lnObjectEntry 21}

lnObjectSharedBy20 OBJECT-TYPE
   SYNTAX INTEGER (1..429496795)
   ACCESS read-only
   STATUS optional
   DESCRIPTION
      "Messages with 20 pointers."
   ::= {lnObjectEntry 22}

lnObjectSharedByGreater OBJECT-TYPE
   SYNTAX INTEGER (1..429496795)
   ACCESS read-only
   STATUS optional
   DESCRIPTION
      "Messages with more than 20 pointers."
   ::= {lnObjectEntry 23}

lnObjectSharedByTotal OBJECT-TYPE
   SYNTAX INTEGER (1..429496795)
   ACCESS read-only
   STATUS optional
   DESCRIPTION
      "The total number of shared messages."
   ::= {lnObjectEntry 24}

--  ******************************************************************
--                      LNDOMINO GROUP
--  ******************************************************************

lnDominoInfo      OBJECT IDENTIFIER ::= {lnDomino 1}
lnDominoCmdInfo   OBJECT IDENTIFIER ::= {lnDomino 2}
lnDominoConfig    OBJECT IDENTIFIER ::= {lnDomino 3}

--  ******************************************************************
--                      LNDOMINOINFO GROUP
--  ******************************************************************

lnDominoBuildName OBJECT-TYPE
   SYNTAX DisplayString
   ACCESS read-only
   STATUS optional
   DESCRIPTION
     "The name given to the build."
   ::= {lnDominoInfo 1}

lnDominoBuildNumber OBJECT-TYPE
   SYNTAX DisplayString
   ACCESS read-only
   STATUS optional
   DESCRIPTION
     "The build number given to the build."
   ::= {lnDominoInfo 2}

lnDominoBuildPlatform OBJECT-TYPE
   SYNTAX DisplayString
   ACCESS read-only
   STATUS optional
   DESCRIPTION
     "The platform this build was created on."
   ::= {lnDominoInfo 3}

lnDominoBuildVersion OBJECT-TYPE
   SYNTAX DisplayString
   ACCESS read-only
   STATUS optional
   DESCRIPTION
     "The version string associated with this build."
   ::= {lnDominoInfo 4}

lnDominoThreadsActivePeak OBJECT-TYPE
   SYNTAX INTEGER (1..429496795)
   ACCESS read-only
   STATUS optional
   DESCRIPTION
     "The peak number of active threads since the Domino server was started."
   ::= {lnDominoInfo 5}

lnDominoThreadsTotal OBJECT-TYPE
   SYNTAX INTEGER (1..429496795)
   ACCESS read-only
   STATUS optional
   DESCRIPTION
     "The total number of available threads to service Domino requests."
   ::= {lnDominoInfo 6}

lnDominoThreadsPeakTotal OBJECT-TYPE
   SYNTAX INTEGER (1..429496795)
   ACCESS read-only
   STATUS optional
   DESCRIPTION
     "The total peak number of active threads since the Domino server was started."
   ::= {lnDominoInfo 7}

lnDominoThreadsPeakTime OBJECT-TYPE
   SYNTAX INTEGER (1..429496795)
   ACCESS read-only
   STATUS optional
   DESCRIPTION
     "The time when the peak number of threads to service Domino requests
      occured, represented as the number of seconds since midnight
      1/1/70 GMT (UNIX epoch)."
   ::= {lnDominoInfo 8}

lnDominoStartTime OBJECT-TYPE
   SYNTAX INTEGER (1..429496795)
   ACCESS read-only
   STATUS optional
   DESCRIPTION
     "The time and date the Domino server was started, represented as the
      number of seconds since midnight 1/1/70 GMT (UNIX epoch)."
   ::= {lnDominoInfo 9}

lnDominoReqPerMinTotal OBJECT-TYPE
   SYNTAX INTEGER (1..429496795)
   ACCESS read-only
   STATUS optional
   DESCRIPTION
     "The total number of Domino requests in the last minute.
      A value of zero may indicate the statistic's value is
      too large to be passed via SNMP."
   ::= {lnDominoInfo 10}

lnDominoReqPerMinPeak OBJECT-TYPE
   SYNTAX INTEGER (1..429496795)
   ACCESS read-only
   STATUS optional
   DESCRIPTION
     "The highest number of Domino requests to occur during
      a one minute interval."
   ::= {lnDominoInfo 11}

lnDominoReqPerMinPeakTime OBJECT-TYPE
   SYNTAX INTEGER (1..429496795)
   ACCESS read-only
   STATUS optional
   DESCRIPTION
     "The time that the peak number of Domino requests occured during
      a one minute interval, represented as the number of seconds since
      midnight 1/1/70 GMT (UNIX epoch)."
   ::= {lnDominoInfo 12}

lnDominoReqPer5MinsTotal OBJECT-TYPE
   SYNTAX INTEGER (1..429496795)
   ACCESS read-only
   STATUS optional
   DESCRIPTION
     "The total number of Domino requests in the last five minutes.
      A value of zero may indicate the statistic's value is
      too large to be passed via SNMP."
   ::= {lnDominoInfo 13}

lnDominoReqPer5MinsPeak OBJECT-TYPE
   SYNTAX INTEGER (1..429496795)
   ACCESS read-only
   STATUS optional
   DESCRIPTION
     "The highest number of Domino requests to occur during a
      five minute interval."
   ::= {lnDominoInfo 14}

lnDominoReqPer5MinsPeakTime OBJECT-TYPE
   SYNTAX INTEGER (1..429496795)
   ACCESS read-only
   STATUS optional
   DESCRIPTION
     "The time that the peak number of Domino requets occured during
      a five minute interval, represented as the number of seconds since
      midnight 1/1/70 GMT (UNIX epoch)."
   ::= {lnDominoInfo 15}

lnDominoReqPerHourTotal OBJECT-TYPE
   SYNTAX INTEGER (1..429496795)
   ACCESS read-only
   STATUS optional
   DESCRIPTION
     "The total number of Domino requetss in the last hour.
      A value of zero may indicate the statistic's value is
      too large to be passed via SNMP."
   ::= {lnDominoInfo 16}

lnDominoReqPerHourPeak OBJECT-TYPE
   SYNTAX INTEGER (1..429496795)
   ACCESS read-only
   STATUS optional
   DESCRIPTION
     "The highest number of Domino requests to occur during a 1 hour interval."
   ::= {lnDominoInfo 17}

lnDominoReqPerHourPeakTime OBJECT-TYPE
   SYNTAX INTEGER (1..429496795)
   ACCESS read-only
   STATUS optional
   DESCRIPTION
     "The time that the peak number of Domino requests occured during a
      one hour interval, represented as the number of seconds since
      midnight 1/1/70 GMT (UNIX epoch)."
   ::= {lnDominoInfo 18}

lnDominoReqPerDayTotal OBJECT-TYPE
   SYNTAX INTEGER (1..429496795)
   ACCESS read-only
   STATUS optional
   DESCRIPTION
     "The total number of Domino requestes in the last day.
      A value of zero may indicate the statistic's value is
      too large to be passed via SNMP."
   ::= {lnDominoInfo 19}

lnDominoReqPerDayPeak OBJECT-TYPE
   SYNTAX INTEGER (1..429496795)
   ACCESS read-only
   STATUS optional
   DESCRIPTION
     "The highest number of Domino requests to occur during a one day interval."
   ::= {lnDominoInfo 20}

lnDominoReqPerDayPeakTime OBJECT-TYPE
   SYNTAX INTEGER (1..429496795)
   ACCESS read-only
   STATUS optional
   DESCRIPTION
     "The time that the peak number of Domino requests occured during
      a one day interval, represented as the number of seconds since
      midnight 1/1/70 GMT (UNIX epoch)."
   ::= {lnDominoInfo 21}

lnDominoRequestsTotal OBJECT-TYPE
   SYNTAX INTEGER (1..429496795)
   ACCESS read-only
   STATUS optional
   DESCRIPTION
     "The total number of Domino requests since the Domino server
      was started.  A value of zero may indicate the statistic's value is
      too large to be passed via SNMP."
   ::= {lnDominoInfo 22}

lnDominoCacheCommandDisplaceRate OBJECT-TYPE
   SYNTAX INTEGER (1..429496795)
   ACCESS read-only
   STATUS optional
   DESCRIPTION
     "Command cache displace rate."
   ::= {lnDominoInfo 23}

lnDominoCacheCommandHitRate OBJECT-TYPE
   SYNTAX INTEGER (1..429496795)
   ACCESS read-only
   STATUS optional
   DESCRIPTION
     "Domino command cache hit rate."
   ::= {lnDominoInfo 24}

lnDominoCacheDatabaseDisplaceRate OBJECT-TYPE
   SYNTAX INTEGER (1..429496795)
   ACCESS read-only
   STATUS optional
   DESCRIPTION
     "Domino database cache displace rate."
   ::= {lnDominoInfo 25}

lnDominoCacheDatabaseHitRate OBJECT-TYPE
   SYNTAX INTEGER (1..429496795)
   ACCESS read-only
   STATUS optional
   DESCRIPTION
     "Domino database cache hit rate."
   ::= {lnDominoInfo 26}

--  ******************************************************************
--                      lnDominoCmdInfo GROUP
--  ******************************************************************

lnDominoCmdInfoEditDocument OBJECT-TYPE
   SYNTAX INTEGER (1..429496795)
   ACCESS read-only
   STATUS optional
   DESCRIPTION
     "The number of EditDocument commands requested since the Domino server was started."
   ::= {lnDominoCmdInfo 1}

lnDominoCmdInfoOpenServer OBJECT-TYPE
   SYNTAX INTEGER (1..429496795)
   ACCESS read-only
   STATUS optional
   DESCRIPTION
     "The number of OpenServer commands requested since the Domino server was started."
   ::= {lnDominoCmdInfo 2}

lnDominoCmdInfoOpenDatabase OBJECT-TYPE
   SYNTAX INTEGER (1..429496795)
   ACCESS read-only
   STATUS optional
   DESCRIPTION
     "The number of OpenDatabase commands requested since the Domino server was started."
   ::= {lnDominoCmdInfo 3}

lnDominoCmdInfoOpenView OBJECT-TYPE
   SYNTAX INTEGER (1..429496795)
   ACCESS read-only
   STATUS optional
   DESCRIPTION
     "The number of OpenView commands requested since the Domino server was started."
   ::= {lnDominoCmdInfo 4}

lnDominoCmdInfoOpenDocument OBJECT-TYPE
   SYNTAX INTEGER (1..429496795)
   ACCESS read-only
   STATUS optional
   DESCRIPTION
     "The number of OpenDocument commands requested since the Domino server was started."
   ::= {lnDominoCmdInfo 5}

lnDominoCmdInfoOpenElement OBJECT-TYPE
   SYNTAX INTEGER (1..429496795)
   ACCESS read-only
   STATUS optional
   DESCRIPTION
     "The number of OpenElement commands requested since the Domino server was started."
   ::= {lnDominoCmdInfo 6}

lnDominoCmdInfoOpenIcon OBJECT-TYPE
   SYNTAX INTEGER (1..429496795)
   ACCESS read-only
   STATUS optional
   DESCRIPTION
     "The number of OpenIcon commands requested since the Domino server was started."
   ::= {lnDominoCmdInfo 7}

lnDominoCmdInfoOpenForm OBJECT-TYPE
   SYNTAX INTEGER (1..429496795)
   ACCESS read-only
   STATUS optional
   DESCRIPTION
     "The number of OpenForm commands requested since the Domino server was started."
   ::= {lnDominoCmdInfo 8}

lnDominoCmdInfoOpenAgent OBJECT-TYPE
   SYNTAX INTEGER (1..429496795)
   ACCESS read-only
   STATUS optional
   DESCRIPTION
     "The number of OpenAgent commands requested since the Domino server was started."
   ::= {lnDominoCmdInfo 9}

lnDominoCmdInfoOpenNavigator OBJECT-TYPE
   SYNTAX INTEGER (1..429496795)
   ACCESS read-only
   STATUS optional
   DESCRIPTION
     "The number of OpenNavigator commands requested since the Domino server was started."
   ::= {lnDominoCmdInfo 10}

lnDominoCmdInfoOpenAbout OBJECT-TYPE
   SYNTAX INTEGER (1..429496795)
   ACCESS read-only
   STATUS optional
   DESCRIPTION
     "The number of OpenAbout commands requested since the Domino server was started."
   ::= {lnDominoCmdInfo 11}

lnDominoCmdInfoOpenHelp OBJECT-TYPE
   SYNTAX INTEGER (1..429496795)
   ACCESS read-only
   STATUS optional
   DESCRIPTION
     "The number of OpenHelp commands requested since the Domino server was started."
   ::= {lnDominoCmdInfo 12}

lnDominoCmdInfoCreateDocument OBJECT-TYPE
   SYNTAX INTEGER (1..429496795)
   ACCESS read-only
   STATUS optional
   DESCRIPTION
     "The number of CreateDocument commands requested since the Domino server
      was started."
   ::= {lnDominoCmdInfo 13}

lnDominoCmdInfoSaveDocument OBJECT-TYPE
   SYNTAX INTEGER (1..429496795)
   ACCESS read-only
   STATUS optional
   DESCRIPTION
     "The number of SaveDocument commands requested since the
     Domino server was started."
   ::= {lnDominoCmdInfo 14}

lnDominoCmdInfoDeleteDocument OBJECT-TYPE
   SYNTAX INTEGER (1..429496795)
   ACCESS read-only
   STATUS optional
   DESCRIPTION
     "The number of DeleteDocument commands requested since the
     Domino server was started."
   ::= {lnDominoCmdInfo 15}

lnDominoCmdInfoSearchSite OBJECT-TYPE
   SYNTAX INTEGER (1..429496795)
   ACCESS read-only
   STATUS optional
   DESCRIPTION
     "The number of SearchSite commands requested since the
     Domino server was started."
   ::= {lnDominoCmdInfo 16}

lnDominoCmdInfoSearchView OBJECT-TYPE
   SYNTAX INTEGER (1..429496795)
   ACCESS read-only
   STATUS optional
   DESCRIPTION
     "The number of SearchView commands requested since the
      Domino server was started."
   ::= {lnDominoCmdInfo 17}

lnDominoCmdInfoUnknown OBJECT-TYPE
   SYNTAX INTEGER (1..429496795)
   ACCESS read-only
   STATUS optional
   DESCRIPTION
     "The number of unrecognized Domino commands."
   ::= {lnDominoCmdInfo 18}

lnDominoCmdInfoLogin OBJECT-TYPE
   SYNTAX INTEGER (1..429496795)
   ACCESS read-only
   STATUS optional
   DESCRIPTION
     "The number of Login commands requested since the Domino server 
      was started."
   ::= {lnDominoCmdInfo 19}

lnDominoCmdInfoNavigate OBJECT-TYPE
   SYNTAX INTEGER (1..429496795)
   ACCESS read-only
   STATUS optional
   DESCRIPTION
     "The number of Navigate commands requested since the Domino server 
      was started."
   ::= {lnDominoCmdInfo 20}

lnDominoCmdInfoReadForm OBJECT-TYPE
   SYNTAX INTEGER (1..429496795)
   ACCESS read-only
   STATUS optional
   DESCRIPTION
     "The number of Read Form commands requested since the Domino server 
      was started."
   ::= {lnDominoCmdInfo 21}

lnDominoCmdInfoTotal OBJECT-TYPE
   SYNTAX INTEGER (1..429496795)
   ACCESS read-only
   STATUS optional
   DESCRIPTION
     "The total number of commands performed since the Domino server 
      was started."
   ::= {lnDominoCmdInfo 22}


--  ******************************************************************
--                      LNDOMINOCONFIG GROUP
--  ******************************************************************

lnDominoCfgPortNumber OBJECT-TYPE
   SYNTAX INTEGER (1..429496795)
   ACCESS read-only
   STATUS optional
   DESCRIPTION
     "The TCP/IP port number from the server record."
   ::= {lnDominoConfig 1}

lnDominoCfgPortStatus OBJECT-TYPE
    SYNTAX INTEGER {
          disabled(0),
          enabled(1)
    }
   ACCESS read-only
   STATUS optional
   DESCRIPTION
     "The TCP/IP port status (enabled or disabled)."
   ::= {lnDominoConfig 2}

lnDominoCfgHostName OBJECT-TYPE
   SYNTAX DisplayString
   ACCESS read-only
   STATUS optional
   DESCRIPTION
     "The HostName of the Domino server."
   ::= {lnDominoConfig 3}

lnDominoCfgDNSLookup OBJECT-TYPE
    SYNTAX INTEGER {
          disabled(0),
          enabled(1)
    }
   ACCESS read-only
   STATUS optional
   DESCRIPTION
     "The status of DNS lookup (enabled or disabled)."
   ::= {lnDominoConfig 4}

lnDominoCfgHomeURL OBJECT-TYPE
   SYNTAX DisplayString
   ACCESS read-only
   STATUS optional
   DESCRIPTION
     "The URL that requests are directed to if only the server name is specified."
   ::= {lnDominoConfig 5}

lnDominoCfgWelcomePage OBJECT-TYPE
   SYNTAX DisplayString
   ACCESS read-only
   STATUS optional
   DESCRIPTION
     "The page name to direct to if no explicit page name is
      specified in the URL."
   ::= {lnDominoConfig 6}

lnDominoCfgActiveThreadsMax OBJECT-TYPE
   SYNTAX INTEGER (1..429496795)
   ACCESS read-only
   STATUS optional
   DESCRIPTION
     "The maximum number of active threads servicing HTTP requests."
   ::= {lnDominoConfig 7}

lnDominoCfgActiveThreadsMin OBJECT-TYPE
   SYNTAX INTEGER (1..429496795)
   ACCESS read-only
   STATUS optional
   DESCRIPTION
     "The minimum number of active threads servicing HTTP requests."
   ::= {lnDominoConfig 8}

lnDominoCfgSSLPortNumber OBJECT-TYPE
   SYNTAX INTEGER (1..429496795)
   ACCESS read-only
   STATUS optional
   DESCRIPTION
     "The TCP/IP port number for HTTP requests using SLL."
   ::= {lnDominoConfig 9}

lnDominoCfgSSLStatus OBJECT-TYPE
    SYNTAX INTEGER {
          disabled(0),
          enabled(1)
    }
   ACCESS read-only
   STATUS optional
   DESCRIPTION
     "The SSL status (enabled or disabled)."
   ::= {lnDominoConfig 10}

lnDominoCfgSSLKeyFile OBJECT-TYPE
   SYNTAX DisplayString
   ACCESS read-only
   STATUS optional
   DESCRIPTION
     "The file name for SSL keys."
   ::= {lnDominoConfig 11}

lnDominoCfgCacheDirectory OBJECT-TYPE
   SYNTAX DisplayString
   ACCESS read-only
   STATUS optional
   DESCRIPTION
     "The directory for the Domino cache."
   ::= {lnDominoConfig 12}

lnDominoCfgCacheSizeMax OBJECT-TYPE
   SYNTAX INTEGER (1..429496795)
   ACCESS read-only
   STATUS optional
   DESCRIPTION
     "The maximum size of the Domino cache in MB."
   ::= {lnDominoConfig 13}

lnDominoCfgCacheDelete OBJECT-TYPE
    SYNTAX INTEGER {
          disabled(0),
          enabled(1)
    }
   ACCESS read-only
   STATUS optional
   DESCRIPTION
     "Delete Domino cache on shutdown (enabled or disabled)."
   ::= {lnDominoConfig 14}

lnDominoCfgGarbageCollectionStatus OBJECT-TYPE
    SYNTAX INTEGER {
          disabled(0),
          enabled(1)
    }
   ACCESS read-only
   STATUS optional
   DESCRIPTION
     "Status of garbage collection (enabled or disabled)."
   ::= {lnDominoConfig 15}

lnDominoCfgGarbageCollectionInterval OBJECT-TYPE
   SYNTAX INTEGER (1..429496795)
   ACCESS read-only
   STATUS optional
   DESCRIPTION
     "The interval between garbage collections in minutes."
   ::= {lnDominoConfig 16}

lnDominoCfgImageFormat OBJECT-TYPE
   SYNTAX DisplayString
   ACCESS read-only
   STATUS optional
   DESCRIPTION
     "Graphics conversion image format."
   ::= {lnDominoConfig 17}

lnDominoCfgImageInterlaced OBJECT-TYPE
    SYNTAX INTEGER {
          disabled(0),
          enabled(1)
    }
   ACCESS read-only
   STATUS optional
   DESCRIPTION
     "Graphics interlacing (enabled or disabled)."
   ::= {lnDominoConfig 18}

lnDominoCfgViewLines OBJECT-TYPE
   SYNTAX INTEGER (1..429496795)
   ACCESS read-only
   STATUS optional
   DESCRIPTION
     "The number of lines per view segment."
   ::= {lnDominoConfig 19}

lnDominoCfgDirectoryHTML OBJECT-TYPE
   SYNTAX DisplayString
   ACCESS read-only
   STATUS optional
   DESCRIPTION
     "The location of the HTML directory setting."
   ::= {lnDominoConfig 20}

lnDominoCfgDirectoryURLPathCGI OBJECT-TYPE
   SYNTAX DisplayString
   ACCESS read-only
   STATUS optional
   DESCRIPTION
     "The CGI URL path."
   ::= {lnDominoConfig 21}

lnDominoCfgDirectoryCGI OBJECT-TYPE
   SYNTAX DisplayString
   ACCESS read-only
   STATUS optional
   DESCRIPTION
     "The location of the CGI directory setting."
   ::= {lnDominoConfig 22}

lnDominoCfgDirectoryURLPathIcons OBJECT-TYPE
   SYNTAX DisplayString
   ACCESS read-only
   STATUS optional
   DESCRIPTION
     "The Domino icons URL path."
   ::= {lnDominoConfig 23}

lnDominoCfgDirectoryIcons OBJECT-TYPE
   SYNTAX DisplayString
   ACCESS read-only
   STATUS optional
   DESCRIPTION
     "The location of the Domino icons directory setting."
   ::= {lnDominoConfig 24}

lnDominoCfgLogAccess OBJECT-TYPE
   SYNTAX DisplayString
   ACCESS read-only
   STATUS optional
   DESCRIPTION
     "The filename for Domino access logs."
   ::= {lnDominoConfig 25}

lnDominoCfgLogError OBJECT-TYPE
   SYNTAX DisplayString
   ACCESS read-only
   STATUS optional
   DESCRIPTION
     "The filename for Domino error logs."
   ::= {lnDominoConfig 26}

lnDominoCfgLogTimeStamp OBJECT-TYPE
   SYNTAX DisplayString
   ACCESS read-only
   STATUS optional
   DESCRIPTION
     "The Domino timestamp format."
   ::= {lnDominoConfig 27}

lnDominoCfgLogFilter OBJECT-TYPE
   SYNTAX DisplayString
   ACCESS read-only
   STATUS optional
   DESCRIPTION
     "The Domino log filter setting."
   ::= {lnDominoConfig 28}

lnDominoCfgTimeoutIdleThread OBJECT-TYPE
   SYNTAX INTEGER (1..429496795)
   ACCESS read-only
   STATUS optional
   DESCRIPTION
     "The interval (in minutes) before idle threads timeout."
   ::= {lnDominoConfig 29}

lnDominoCfgTimeoutInput OBJECT-TYPE
   SYNTAX INTEGER (1..429496795)
   ACCESS read-only
   STATUS optional
   DESCRIPTION
     "The interval (in minutes) before timeout expires while waiting for input."
   ::= {lnDominoConfig 30}


lnDominoCfgTimeoutOutput OBJECT-TYPE
   SYNTAX INTEGER (1..429496795)
   ACCESS read-only
   STATUS optional
   DESCRIPTION
     "The interval (in minutes) before timeout expires while waiting for output."
   ::= {lnDominoConfig 31}

lnDominoCfgTimeoutCGI OBJECT-TYPE
   SYNTAX INTEGER (1..429496795)
   ACCESS read-only
   STATUS optional
   DESCRIPTION
     "The interval (in minutes) before CGI timeout expires while waiting for input."
   ::= {lnDominoConfig 32}

--  ******************************************************************
--  Here are the statistics for the Calendaring and Scheduling package
--  ******************************************************************

lnCalTotalAllApptsResources OBJECT-TYPE
    SYNTAX INTEGER (1..429496795)
    ACCESS read-only
    STATUS optional
    DESCRIPTION
      "The total number of scheduled appointment and resource reservations."
    ::= {lnCalendar 1}

lnCalTotalAllUsersResources OBJECT-TYPE
    SYNTAX INTEGER (1..429496795)
    ACCESS read-only
    STATUS optional
    DESCRIPTION
      "The total number of resources that have been reserved, plus
       the number of users with scheduled appointments."
    ::= {lnCalendar 2}

lnCalTotalAppointments OBJECT-TYPE
    SYNTAX INTEGER (1..429496795)
    ACCESS read-only
    STATUS optional
    DESCRIPTION
      "The total number of scheduled appointments."
    ::= {lnCalendar 3}

lnCalTotalReservations OBJECT-TYPE
    SYNTAX INTEGER (1..429496795)
    ACCESS read-only
    STATUS optional
    DESCRIPTION
      "The total number of reservations for resources."
    ::= {lnCalendar 4}

lnCalTotalResources OBJECT-TYPE
    SYNTAX INTEGER (1..429496795)
    ACCESS read-only
    STATUS optional
    DESCRIPTION
      "The total number of resources that have been reserved."
    ::= {lnCalendar 5}

lnCalTotalUsers OBJECT-TYPE
    SYNTAX INTEGER (1..429496795)
    ACCESS read-only
    STATUS optional
    DESCRIPTION
      "The total number of users that have scheduled appointments."
    ::= {lnCalendar 6}

--  ******************************************************************
--                      LNCOLLECTOR GROUP
--  ******************************************************************

lnCollectorTimeCollected OBJECT-TYPE
    SYNTAX INTEGER (0..4294967295)
    ACCESS read-only
    STATUS mandatory
    DESCRIPTION
      "Time and date at which the statistics collector task last
       collected statistics; represented as the number of seconds
       since midnight 1/1/70 GMT (UNIX epoch)."
    ::= { lnCollector 1 }

lnCollectorTimeElapsed OBJECT-TYPE
    SYNTAX DisplayString
    ACCESS read-only
    STATUS mandatory
    DESCRIPTION
      "The time that has elapsed since the statistics collector
       task was started."
    ::= { lnCollector 2 }

--  ******************************************************************
--                       LNINFO SCALAR OBJECTS
--  ******************************************************************

lnMIBVersion OBJECT-TYPE
    SYNTAX DisplayString
    ACCESS read-only
    STATUS mandatory
    DESCRIPTION
       "Domino SNMP support level (MIB Version)."
    ::= { lnInfo 3 }

lnQSBuildNumber OBJECT-TYPE
    SYNTAX DisplayString
    ACCESS read-only
    STATUS mandatory
    DESCRIPTION
      "The build number of the Query/Set Notes add-in task."
    ::= {lnInfo 5}


--  ******************************************************************
--                       lNCLUSTER GROUP
--  ******************************************************************

lnClusterName OBJECT-TYPE
    SYNTAX DisplayString
    ACCESS read-only
    STATUS optional
    DESCRIPTION
      "The name of the cluster this server is a member of."
    ::= { lnCluster 1 }

lnClusterAvailIndex OBJECT-TYPE
    SYNTAX INTEGER (0..100)
    ACCESS read-only
    STATUS optional
    DESCRIPTION
      "The current percentage or an index of the current server's
       availability.  A value of 0 indicates that the server has
       virtually no available resources.  A value of 100 indicates
       that the server is completely available."
    ::= { lnCluster 2 }

lnClusterAvailThreshold OBJECT-TYPE
    SYNTAX INTEGER (0..4294967295)
    ACCESS read-only
    STATUS optional
    DESCRIPTION
      "The current setting of this server's availability threshold.
       The value is compared against lnClusterAvailIndex.
       BUSY - The availability index has dropped below the threshold."
    ::= { lnCluster 3 }

lnClusterPortName OBJECT-TYPE
    SYNTAX DisplayString
    ACCESS read-only
    STATUS optional
    DESCRIPTION
      "Default PortName being used for intra cluster network traffic.
       There is no default port. Any available and active port may
       be used for intra cluster traffic."
    ::= { lnCluster 4 }

lnClusterProbeCount OBJECT-TYPE
    SYNTAX INTEGER (0..4294967295)
    ACCESS read-only
    STATUS optional
    DESCRIPTION
      "The total number of times this cluster member has completed a
       probe request for another cluster member."
    ::= { lnCluster 5 }

lnClusterProbeTimeout OBJECT-TYPE
    SYNTAX INTEGER (0..4294967295)
    ACCESS read-only
    STATUS optional
    DESCRIPTION
      "In Minutes.  The interval between intra cluster probes or
       cluster member heartbeats."
    ::= { lnCluster 6 }

lnClusterTable OBJECT-TYPE
    SYNTAX SEQUENCE OF lnClusterEntry
    ACCESS read-only
    STATUS optional
    DESCRIPTION
      "A table containing one entry for each configured Notes server
      cluster member known by this server."
    ::= { lnCluster 7 }

lnClusterProbeError OBJECT-TYPE
    SYNTAX INTEGER (0..4294967295)
    ACCESS read-only
    STATUS optional
    DESCRIPTION
      "The number of times a server received an error while
       probing another server."
    ::= { lnCluster 11 }

lnClusterEntry OBJECT-TYPE
    SYNTAX lnClusterEntry
    ACCESS read-only
    STATUS optional
    DESCRIPTION
      "The entry type definition for the lnClusterTable."
    INDEX { lnClusterTableIndex }
    ::= { lnClusterTable 1 }

lnClusterEntry ::= SEQUENCE {
    lnClusterTableIndex     INTEGER,
    lnClusterMemberName     DisplayString,
    lnClusterMemberIndex    DisplayString
    }

lnClusterTableIndex OBJECT-TYPE
    SYNTAX INTEGER (1..2147483647)
    ACCESS read-only
    STATUS optional
    DESCRIPTION
      "A unique value for each entry in the lnClusterTable."
    ::= { lnClusterEntry 1 }

lnClusterMemberName OBJECT-TYPE
    SYNTAX DisplayString
    ACCESS read-only
    STATUS optional
    DESCRIPTION
      "Name of Notes Cluster Member."
    ::= { lnClusterEntry 2 }

lnClusterMemberIndex OBJECT-TYPE
    SYNTAX DisplayString
    ACCESS read-only
    STATUS optional
    DESCRIPTION
      "The last known load information for a cluster member."
    ::= { lnClusterEntry 3 }


--  ******************************************************************
--                       LNOPENREDIRECTS GROUP
--  ******************************************************************

lnClusterFailoverByPathSucc OBJECT-TYPE
    SYNTAX INTEGER (0..4294967295)
    ACCESS read-only
    STATUS optional
    DESCRIPTION
      "The number of times this server was successfully able
      to redirect a client to another cluster member after the
      client was unable to open a database by pathname on
      a cluster member."
    ::= { lnOpenRedirects 1 }

lnClusterFailoverByPathUnsucc OBJECT-TYPE
    SYNTAX INTEGER (0..4294967295)
    ACCESS read-only
    STATUS optional
    DESCRIPTION
      "The number of times this server was unsuccessful at
      redirecting a client to another cluster member after the
      client was unable to open a database by pathname for
      a cluster member."
    ::= { lnOpenRedirects 2 }

lnClusterFailoverSucc OBJECT-TYPE
    SYNTAX INTEGER (0..4294967295)
    ACCESS read-only
    STATUS optional
    DESCRIPTION
      "The number of times this server was successfully
      able to redirect a client to another cluster member
      after the client was unable to open a database by
      replica ID on a cluster member."
    ::= { lnOpenRedirects 3 }

lnClusterFailoverUnsucc OBJECT-TYPE
    SYNTAX INTEGER (0..4294967295)
    ACCESS read-only
    STATUS optional
    DESCRIPTION
     "The number of times this server was unsuccessful at
      redirecting a client to another cluster member after the
      client was unable to open a database by replica ID on
      a cluster member."
    ::= { lnOpenRedirects 4 }

lnClusterLoadBalByPathSucc OBJECT-TYPE
    SYNTAX INTEGER (0..4294967295)
    ACCESS read-only
    STATUS optional
    DESCRIPTION
     "The number of times this server was successfully able to
      redirect a client to another cluster member after the client
      attempted to open a database by pathname on a cluster
      member that was BUSY."
    ::= { lnOpenRedirects 5 }

lnClusterLoadBalByPathUnsucc OBJECT-TYPE
    SYNTAX INTEGER (0..4294967295)
    ACCESS read-only
    STATUS optional
    DESCRIPTION
     "The number of times this server was unsuccessful at
      redirecting a client to another cluster member after the
      client attempted to open a database by pathname on a
      cluster member that was BUSY."
    ::= { lnOpenRedirects 6 }

lnClusterLoadBalSucc OBJECT-TYPE
    SYNTAX INTEGER (0..4294967295)
    ACCESS read-only
    STATUS optional
    DESCRIPTION
     "The number of times this server was successfully able to
      redirect a client to another cluster member after the client
      attempted to open a database by replica ID on a cluster
      member that was BUSY."
    ::= { lnOpenRedirects 7 }

lnClusterLoadBalUnsucc OBJECT-TYPE
    SYNTAX INTEGER (0..4294967295)
    ACCESS read-only
    STATUS optional
    DESCRIPTION
     "The number of times this server was unsuccessful at
      redirecting a client to another cluster member after the
      client attempted to open a database by replica ID on
      a cluster member that was BUSY."
    ::= { lnOpenRedirects 8 }



--  ******************************************************************
--                       lnOpenRequest GROUP
--  ******************************************************************

lnClusterOpenReqClustBusy OBJECT-TYPE
    SYNTAX INTEGER (0..4294967295)
    ACCESS read-only
    STATUS optional
    DESCRIPTION
     "The number of times that a client attempted to open a
      database on this cluster member when it and the rest
      of the cluster were BUSY."
    ::= { lnOpenRequest 1 }

lnClusterOpenReqDBOutofServ OBJECT-TYPE
    SYNTAX INTEGER (0..4294967295)
    ACCESS read-only
    STATUS optional
    DESCRIPTION
      "The number of times a client attempted to open a database
       that has been marked as out of service on this cluster
       member."
    ::= { lnOpenRequest 2 }

lnClusterOpenReqLoadBalanced OBJECT-TYPE
    SYNTAX INTEGER (0..4294967295)
    ACCESS read-only
    STATUS optional
    DESCRIPTION
      "The number of times a client attempted to open a database
       on this cluster member when the cluster member was BUSY."
    ::= { lnOpenRequest 3 }


--  ******************************************************************
--                       LNCLUSTERTRANS GROUP
--  ******************************************************************

lnClusterTransIntAvgTime OBJECT-TYPE
    SYNTAX INTEGER (0..4294967295)
    ACCESS read-only
    STATUS optional
    DESCRIPTION
      "Average transaction time (in milliseconds) for this
       member of the cluster.  Based on transaction data
       captured over a number of recent intervals of time."
    ::= { lnClusterTrans 1 }

lnClusterTransIntInSec OBJECT-TYPE
    SYNTAX INTEGER (0..4294967295)
    ACCESS read-only
    STATUS optional
    DESCRIPTION
      "Current setting for the length of the intervals.
       Used to capture transaction data for load balance
       computations."
    ::= { lnClusterTrans 2 }

lnClusterTransIntUsedInAvg OBJECT-TYPE
    SYNTAX INTEGER (0..4294967295)
    ACCESS read-only
    STATUS optional
    DESCRIPTION
      "Current setting of the number for intervals being
       used to capture transaction data on load balance
       computations."
    ::= { lnClusterTrans 3 }

lnClusterTransLastIntAvgTime OBJECT-TYPE
    SYNTAX INTEGER (0..4294967295)
    ACCESS read-only
    STATUS optional
    DESCRIPTION
      "Average transaction time for the last interval of
       transaction data captured on this cluster member."
    ::= { lnClusterTrans 4 }

lnClusterTransNormValue OBJECT-TYPE
    SYNTAX INTEGER (0..4294967295)
    ACCESS read-only
    STATUS optional
    DESCRIPTION
      "The current setting for the acceptable average
       transaction time (in milliseconds) on this cluster
       member."
    ::= { lnClusterTrans 5 }


--  ******************************************************************
--                       LNCONTROL GROUP
--  ******************************************************************

lnNotesServerSetState OBJECT-TYPE
    SYNTAX INTEGER {
      up(1),
      down(2)
    }
    ACCESS read-write
    STATUS mandatory
    DESCRIPTION
      "Set to 'down' to shut Notes server down, set to 'up' to
       restart Notes server.  Note: access to this feature is
       controlled through external (non-SNMP) security measures."
    ::= { lnControl 1 }

lnNotesServerState OBJECT-TYPE
    SYNTAX INTEGER {
      up(1),
      down(2),
      not-responding(3),
      crashed(4),
      unknown(5)
    }
    ACCESS read-only
    STATUS mandatory
    DESCRIPTION
      "Equals 'down' if the Notes server is down, equals 'up'
       if the Notes server is running."
    ::= { lnControl 2 }

lnLastTrapSeq OBJECT-TYPE
    SYNTAX INTEGER (1..2147483647)
    ACCESS read-only
    STATUS mandatory
    DESCRIPTION
      "Sequence number of last trap sent.  Same as the
       index number that trap in the lnRecentTrapsTable."
    ::= { lnControl 3 }

lnRecentTrapsTable OBJECT-TYPE
    SYNTAX SEQUENCE OF lnRecentTrapsEntry
    ACCESS not-accessible
    STATUS mandatory
    DESCRIPTION
      "A table containing the last 10 generated traps."
    ::= { lnControl 4 }

lnRecentTrapsEntry OBJECT-TYPE
    SYNTAX lnRecentTrapsEntry
    ACCESS not-accessible
    STATUS mandatory
    DESCRIPTION
      "The entry type definition for the lnRecentTrapsTable."
    INDEX { lnTrapSeq }
    ::= { lnRecentTrapsTable 1 }

lnRecentTrapsEntry ::= SEQUENCE {
    lnTrapSeq   INTEGER,
    lnTrapInfo  DisplayString
}

lnTrapSeq OBJECT-TYPE
    SYNTAX INTEGER (1..2147483647)
    ACCESS read-only
    STATUS mandatory
    DESCRIPTION
      "A unique value for each trap record in
       the sequence of entries returned to the
       lnRecentTrapsTable."
    ::= { lnRecentTrapsEntry 1 }

lnTrapInfo OBJECT-TYPE
    SYNTAX DisplayString
    ACCESS read-only
    STATUS mandatory
    DESCRIPTION
      "A string containing the information for a trap."
    ::= { lnRecentTrapsEntry 2 }

lnRemoteReboot OBJECT-TYPE
    SYNTAX INTEGER {
      no(1),
      yes(2)
    }
    ACCESS read-write
    STATUS mandatory
    DESCRIPTION
      "Set to 'yes' to reboot the entire system.
       This value will be returned as 'yes' if the system is in
       the process of rebooting but hasn't come down yet"
    ::= { lnControl 5 }

lnServerTbl OBJECT-TYPE
    SYNTAX SEQUENCE OF lnRecentTrapsEntry
    ACCESS not-accessible
    STATUS optional
    DESCRIPTION
     "A table containing the list of Domino Servers that have been
      partitioned across this machine.  This must be configured by the
      system administrator.  This table only reflects the Domino Servers
      that are listed in the file lnsnmp.ini since there is no way to
      query a given machine for a list of potentially available servers."
    ::= { lnControl 6 }

lnTotalPartitions OBJECT-TYPE
    SYNTAX INTEGER (1..2147483647)
    ACCESS read-only
    STATUS mandatory
    DESCRIPTION
      "If the file lnsnmp.ini exists, this MIB variable will represent
       the number of 'Server=' entries in that file.  If the file lnsnmp.ini
       does not exist, the value of lnTotalPartitions will equal zero."
    ::= { lnControl 7 }

lnMPAIniFileLocation OBJECT-TYPE
    SYNTAX DisplayString
    ACCESS read-only
    STATUS mandatory
    DESCRIPTION
      "The directory that the file lnsnmp.ini was read from.
       Normally this is either the Windows-NT directory or this will
       be /opt/lotus for UNIX systems.  However, on either platform, if
       the file is not found, the PATH environment variable will be
       searched.  The first instance of lnsnmp.ini in the PATH will
       be opened."
    ::= { lnControl 8 }

lnServerTblEntry OBJECT-TYPE
    SYNTAX lnRecentTrapsEntry
    ACCESS not-accessible
    STATUS optional
    DESCRIPTION
      "The entry type definition for the lnServerTbl."
    INDEX { lnServerTblIndex }
    ::= { lnServerTbl 1 }

lnServerTblEntry ::= SEQUENCE {
    lnServerTblIndex          Integer,
    lnServerTblName           DisplayString,
    lnServerTblNotesPartition Integer,
    lnServerTblDataDir        DisplayString,
    lnServerTblDataDirValid   Integer,
    lnServerTblState          Integer,
    lnServerIdentifiedItself  Integer,
    lnServerTblSetState       Integer
}

lnServerTblIndex OBJECT-TYPE
    SYNTAX INTEGER (1..2147483647)
    ACCESS read-only
    STATUS optional
    DESCRIPTION
      "The MIB index for this row in the lnServerTbl."
    ::= { lnServerTblEntry 1 }

lnServerTblName OBJECT-TYPE
    SYNTAX DisplayString
    ACCESS read-only
    STATUS optional
    DESCRIPTION
      "The name of the server as it appears in lnsnmp.ini.
       However, if a server's addin task registers with the Main Proxy Agent,
       The addin task will update the server's name with the correct name
       if a match can be found."
    ::= { lnServerTblEntry 2 }

lnServerTblNotesPartition OBJECT-TYPE
    SYNTAX INTEGER (1..2147483647)
    ACCESS read-only
    STATUS optional
    DESCRIPTION
      "The value that is entered in lnsnmp.ini.
       This MUST match the environment variable NOTESPARTITION for
       Domino Servers partitioned on Windows-NT Systems.  This
       has no real meaning for Domino Servers on UNIX platforms."
    ::= { lnServerTblEntry 3 }

lnServerTblDataDir OBJECT-TYPE
    SYNTAX DisplayString
    ACCESS read-only
    STATUS optional
    DESCRIPTION
      "The data directory of the given Domino server as entered
       in lnsnmp.ini;  See lnServerTblDataDirValid for an indication on
       whether or not this is a valid Domino Server data directory."
    ::= { lnServerTblEntry 4 }

lnServerTblDataDirValid OBJECT-TYPE
    SYNTAX INTEGER {
      True(1),
      False(2)
    }
    ACCESS read-only
    STATUS optional
    DESCRIPTION
      "The Main Proxy Agent validates the Domino Server data directory
       that is entered in lnsnmp.ini.  This will be TRUE if this is a valid
       directory and the file notes.ini exists within that directory.
       It will be false otherwise."
    ::= { lnServerTblEntry 5}

lnServerTblState OBJECT-TYPE
    SYNTAX INTEGER {
      Up(1),
      Down(2)
    }
    ACCESS read-only
    STATUS optional
    DESCRIPTION
      "This will indicate the current state of the server.  The server will
       be considered down until at least one of the Domino Management Agent 
       tasks starts and registers with the Main Proxy Agent."
    ::= { lnServerTblEntry 6 }

lnServerIdentifiedItself OBJECT-TYPE
    SYNTAX INTEGER {
      True(1),
      False(2)
    }
    ACCESS read-only
    STATUS optional
    DESCRIPTION
      "This will indicate if the server has ever run and identified
       itself to the Main Proxy Agent at any time during the current
       lifespan of the Main Proxy Agent.  This may be used as an
       indication that a given Domino server may not be configured
       correctly in lnsnmp.ini.  The server identification occurs when
       one of the Domino Management Agent addin tasks is started."
    ::= { lnServerTblEntry 7 }

lnServerTblSetState OBJECT-TYPE
    SYNTAX INTEGER {
      Up(1),
      Down(2)
    }
    ACCESS read-write
    STATUS optional
    DESCRIPTION
      "This will indicate the current state of the Domino server and
       allow remote SNMP control over stopping & starting the Domion
       server.  The server will be considered down until at least one
       of the Domino management Agent addin tasks starts and registers 
       with the Main Proxy Agent."
    ::= { lnServerTblEntry 8 }


--  ******************************************************************
--                      LNINTERCEPTOR GROUP
--  ******************************************************************

lnEvtServer OBJECT-TYPE
    SYNTAX DisplayString
    ACCESS read-only
    STATUS mandatory
    DESCRIPTION
      "Originating server for this event."
    ::= { lnInterceptor 1 }

lnEvtType OBJECT-TYPE
    SYNTAX INTEGER {
          unknown(0),
          communications(1),
          security(2),
          mail(3),
          replication(4),
          resource(5),
          miscellaneous(6),
          server(7),
          alarm(8)
    }
    ACCESS read-only
    STATUS mandatory
    DESCRIPTION
      "Returns a value for the type of this event."
    ::= { lnInterceptor 2 }

lnEvtSeverity OBJECT-TYPE
    SYNTAX INTEGER {
          unknown(0),
          fatal(1),
          failure(2),
          warning1(3),
          warning2(4),
          normal(5)
        }
    ACCESS read-only
    STATUS mandatory
    DESCRIPTION
      "Returns a value for the severity of this event."
    ::= { lnInterceptor 3 }

lnEvtWhen OBJECT-TYPE
    SYNTAX INTEGER (0..4294967295)
    ACCESS read-only
    STATUS mandatory
    DESCRIPTION
      "Returns a value for the date and time of this event."
    ::= { lnInterceptor 4 }

lnEvtData OBJECT-TYPE
    SYNTAX DisplayString
    ACCESS read-only
    STATUS mandatory
    DESCRIPTION
      "Information about this event."
    ::= { lnInterceptor 5 }

lnEvtSeq OBJECT-TYPE
    SYNTAX INTEGER (1..2147483647)
    ACCESS read-only
    STATUS mandatory
    DESCRIPTION
      "Sequence number of this event for internal
       use only.  This information is not available in
       this MIB variable.  If you wish to determine the
       sequence number for the last trap, please see
       the variable lnControl.lnRecentTrapsTable.lnRecentTrapEntry.lnTrapSeq."
    ::= { lnInterceptor 6 }

--  ** Define the Unix specific variables.

lnAlarm OBJECT IDENTIFIER ::= { lnUnix 1 }
lnSignal OBJECT IDENTIFIER ::= { lnUnix 2 }

--  ** Define the trap variables used in the Alarm Manager, nvalarmgrd

lnAlarmServerHandle OBJECT-TYPE
    SYNTAX INTEGER (0..4294967295)
    ACCESS not-accessible
    STATUS optional
    DESCRIPTION
      "This represents the server for which the alarm will be generated for."
    ::= {lnAlarm 1}

lnAlarmTargetHandle OBJECT-TYPE
    SYNTAX INTEGER (0..4294967295)
    ACCESS not-accessible
    STATUS optional
    DESCRIPTION
      "This represents the entity on the server that caused the alarm 
       to be generated"
    ::= {lnAlarm 2}

lnAlarmDate OBJECT-TYPE
    SYNTAX INTEGER (0..4294967295)
    ACCESS not-accessible
    STATUS optional
    DESCRIPTION
      "The date the alarm occured."
    ::= {lnAlarm 3}

lnAlarmTime OBJECT-TYPE
    SYNTAX INTEGER (0..4294967295)
    ACCESS not-accessible
    STATUS optional
    DESCRIPTION
      "The time the alarm occured."
    ::= {lnAlarm 4}

lnAlarmSeverity OBJECT-TYPE
    SYNTAX INTEGER {
        normal(0),
        informational(1),
        disabled(2),
        unmanaged(3),
        unknown(4),
        marginal(5),
        warning(6),
        minor(7),
        major(8),
        critical(9)
    }
    ACCESS not-accessible
    STATUS optional
    DESCRIPTION
      "The severity of the alarm being generated by the SNMP trap"
    ::= {lnAlarm 5}

lnAlarmIntArg OBJECT-TYPE
   SYNTAX INTEGER (0..2147483647)
   ACCESS not-accessible
   STATUS optional
   DESCRIPTION
     "Returns a value for the integer argument associated with the Alarm."
   ::= {lnAlarm 6}

lnAlarmLongArg OBJECT-TYPE
   SYNTAX INTEGER (0..4294967295)
   ACCESS not-accessible
   STATUS optional
   DESCRIPTION
     "The long integer argument associated with the Alarm."
   ::= {lnAlarm 7}

lnAlarmDoubleArg OBJECT-TYPE
   SYNTAX OCTET STRING
   ACCESS not-accessible
   STATUS optional
   DESCRIPTION
     "The string representation of a floating point value."
   ::= {lnAlarm 8}

lnAlarmTextArg1 OBJECT-TYPE
   SYNTAX OCTET STRING
   ACCESS not-accessible
   STATUS optional
   DESCRIPTION
     "The first text argument associated with the Alarm."
   ::= {lnAlarm 9}

lnAlarmTextArg2 OBJECT-TYPE
   SYNTAX OCTET STRING
   ACCESS not-accessible
   STATUS optional
   DESCRIPTION
     "The second text argument associated with the Alarm."
   ::= {lnAlarm 10}

lnAlarmSeverityStr OBJECT-TYPE
   SYNTAX DisplayString
   ACCESS not-accessible
   STATUS optional
   DESCRIPTION
     "A string representation of the alarm severity.  This is
      used in the trap that is sent to the management station to
      be displayed on the NetView event cards."
   ::= {lnAlarm 11}

lnAlarmTypeStr OBJECT-TYPE
   SYNTAX DisplayString
   ACCESS not-accessible
   STATUS optional
   DESCRIPTION
     "A string representation of the alarm's type.  This is
      used in the trap that is sent to the management station to
      be displayed on the NetView event cards."
   ::= {lnAlarm 12}

lnAlarmMessage OBJECT-TYPE
   SYNTAX DisplayString
   ACCESS not-accessible
   STATUS optional
   DESCRIPTION
     "A message indicating why the alarm was raised.  This is
      used in the trap that is sent to the management station to
      be displayed on the NetView event cards."
   ::= {lnAlarm 13}

lnAlarmMessageExt OBJECT-TYPE
   SYNTAX DisplayString
   ACCESS not-accessible
   STATUS optional
   DESCRIPTION
     "A message extension with more detailed information explaining
      why the alarm was raised.  This is used in the trap that is sent
      to the management station to be displayed on the NetView event
      cards."
   ::= {lnAlarm 14}

lnAlarmServerName OBJECT-TYPE
   SYNTAX DisplayString
   ACCESS not-accessible
   STATUS optional
   DESCRIPTION
     "The server name of the Notes server the alarm was raised
      against.  This is used in the trap that is sent to the management
      station to be displayed in the NetView event cards."
   ::= {lnAlarm 15}

--Define some variables for signals and messages

lnSignalServerId OBJECT-TYPE
    SYNTAX INTEGER (0..4294967295)
    ACCESS not-accessible
    STATUS optional
    DESCRIPTION
      "This variable will be embedded in the lnSignalServerConfigChg trap.
       This is an integer that represents the ServerId of the
       Notes server that caused the signal to be raised."
    ::= {lnSignal 1}

lnSignalOldServerType OBJECT-TYPE
    SYNTAX INTEGER (0..4294967295)
    ACCESS not-accessible
    STATUS optional
    DESCRIPTION
      "This variable will be embedded in the lnSignalServerConfigChg trap.
       This is an the integer value representing the old server class."
    ::= {lnSignal 2}

lnSignalNewServerType OBJECT-TYPE
    SYNTAX INTEGER (0..4294967295)
    ACCESS not-accessible
    STATUS optional
    DESCRIPTION
      "This variable will be embedded in the lnSignalServerConfigChg trap.
       This is an integer value representing the new server class."
    ::= {lnSignal 3}

lnSignalWhatHasChanged OBJECT-TYPE
    SYNTAX INTEGER (0..4294967295)
    ACCESS not-accessible
    STATUS optional
    DESCRIPTION
      "This variable will be embedded in the lnSignalServerConfigChg trap.
       This is an integer value indicating what has changed on
        the server."
    ::= {lnSignal 4}

lnSignalServerName OBJECT-TYPE
   SYNTAX DisplayString
   ACCESS not-accessible
   STATUS optional
   DESCRIPTION
     "The server name.  This will appear in the information trap
      displayed in the NetView Event Cards when a specific server has
      had all its alarms cleared."
   ::= {lnSignal 5}



--Define the traps

lnUnknownEventTrap TRAP-TYPE
    ENTERPRISE Notes
    VARIABLES   { lnEvtServer, lnEvtType, lnEvtSeverity,
                  lnEvtWhen, lnEvtData, lnEvtSeq }
    DESCRIPTION
      "This trap indicates that a Notes Event of Unknown severity
       has occurred.  Configuration of which events generated traps
       is performed in the Public Address book."
    ::= 0

lnFatalEventTrap TRAP-TYPE
    ENTERPRISE Notes
    VARIABLES   { lnEvtServer, lnEvtType, lnEvtSeverity,
                  lnEvtWhen, lnEvtData, lnEvtSeq }
    DESCRIPTION
      "This trap indicates that a Notes Event of Fatal severity
       has occurred.  Configuration of which events generated traps
       is performed in the Public Address book."
    ::= 1

lnFailureEventTrap TRAP-TYPE
    ENTERPRISE Notes
    VARIABLES   { lnEvtServer, lnEvtType, lnEvtSeverity,
                  lnEvtWhen, lnEvtData, lnEvtSeq }
    DESCRIPTION
      "This trap indicates that a Notes Event of Failure severity
       has occurred.  Configuration of which events generated traps
       is performed in the Public Address book."
    ::= 2

lnWarning1EventTrap TRAP-TYPE
    ENTERPRISE Notes
    VARIABLES   { lnEvtServer, lnEvtType, lnEvtSeverity,
                  lnEvtWhen, lnEvtData, lnEvtSeq }
    DESCRIPTION
      "This trap indicates that a Notes Event of Warning1 severity
       has occurred.  Configuration of which events generated traps
       is performed in the Public Address book."
    ::= 3

lnWarning2EventTrap TRAP-TYPE
    ENTERPRISE Notes
    VARIABLES   { lnEvtServer, lnEvtType, lnEvtSeverity,
                  lnEvtWhen, lnEvtData, lnEvtSeq }
    DESCRIPTION
      "This trap indicates that a Notes Event of Warning2 severity
       has occurred.  Configuration of which events generated traps
       is performed in the Public Address book."
    ::= 4

lnNormalEventTrap TRAP-TYPE
    ENTERPRISE Notes
    VARIABLES   { lnEvtServer, lnEvtType, lnEvtSeverity,
                  lnEvtWhen, lnEvtData, lnEvtSeq }
    DESCRIPTION
      "This trap indicates that a Notes Event of Normal severity
       has occurred.  Configuration of which events generated traps
       is performed in the Public Address book."
    ::= 5


lnServerUpTrap TRAP-TYPE
    ENTERPRISE Notes
    VARIABLES   { lnEvtServer }
    DESCRIPTION
      "This trap indicates that the Notes server has come up."
    ::= 11

lnServerDownTrap TRAP-TYPE
    ENTERPRISE Notes
    VARIABLES   { lnEvtServer }
    DESCRIPTION
      "This trap indicates that the Notes server has gone down."
    ::= 12

lnServerPulseFailedTrap TRAP-TYPE
    ENTERPRISE Notes
    VARIABLES   { lnEvtServer }
    DESCRIPTION
      "This trap indicates that the Notes server is not responding
       to the Lotus Notes SNMP agent.  The server may have crashed,
       or may be busy."
    ::= 13

lnServerPulseRestoredTrap TRAP-TYPE
    ENTERPRISE Notes
    VARIABLES   { lnEvtServer }
    DESCRIPTION
      "This trap indicates that the Notes server is now responding
       to the Lotus Notes SNMP agent."
    ::= 14

lnSystemRebootingTrap TRAP-TYPE
    ENTERPRISE Notes
    DESCRIPTION
      "This trap indicates that the operating system the Notes server is
       running has recieved an SNMP reboot request.  The system is
       now rebooting, this may take up to 5 minutes."
    ::= 15

lnServerNotRespondingTrap TRAP-TYPE
    ENTERPRISE Notes
    VARIABLES   { lnEvtServer }
    DESCRIPTION
      "This trap indicates that the Notes server has not responded
       to the Lotus Notes SNMP agent for several minutes.  There is
       a chance that the Notes server may have crashed."
    ::= 16

lnServerNowRespondingTrap TRAP-TYPE
    ENTERPRISE Notes
    VARIABLES   { lnEvtServer }
    DESCRIPTION
      "This trap indicates that the Notes server is now responding
       to the Lotus Notes SNMP agent after failing to respond for several
       minutes.  The server may be overloaded."
    ::= 17

--
--"Alarm" traps generated by NotesView for AIX (or future Unix ports)
--

lnAlarmStatisticThreshold TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX when an alarm statistic
        threshold is hit"
    ::= 30

lnAlarmServerStatusChange TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX when the alarm status
       of the server changes."
    ::= 31

lnAlarmPortStatusChange TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX when the alarm status
       of a port changes."
    ::= 32

lnAlarmTaskStatusChange TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX when the alarm status
      of a permanent task changes."
    ::= 33

lnAlarmNVStatClear TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX to indicate that
       an alarm statistic threshold condition has been cleared."
    ::= 34

lnAlarmAutoDiscovery TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX to indicate a discrepancy
        between the information that Autodiscovery has detected, and what
        the server has reported."
    ::= 35

lnAlarmServerNotesEvent TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX when a Notes
       server event occurs."
    ::= 36

lnAlarmServerCfgChangeEvent TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX if the server
       configuration has changed."
    ::= 37

lnAlarmMailProbeEvent TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX if the Mail Probe
        task needs to generate an alarm."
    ::= 38

lnAlarmNSFRemoteConsoleEvent TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX if the there is an
       NSF remote console event"
    ::= 40

lnAlarmMailBoxEvent TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX if the there
       is a MailBox event."
    ::= 41

lnAlarmServerSNMPEvent TRAP-TYPE
    ENTERPRISE Notes
    VARIABLES   { lnAlarmServerHandle, lnAlarmTargetHandle,  lnAlarmDate,
                  lnAlarmTime, lnAlarmSeverity lnAlarmIntArg, lnAlarmLongArg,
                  lnAlarmDoubleArg, lnAlarmTextArg1, lnAlarmTextArg2}
    DESCRIPTION
      "This trap is sent by NotesView for AIX if the there is an
       SNMP event that generates an alarm."
    ::= 39

lnAlarmClearAll  TRAP-TYPE
    ENTERPRISE Notes
    DESCRIPTION
      "This trap is sent by NotesView for AIX to cause the
       alarm manager daemon (nvalarmgrd) to clear all alarms for all
       servers and connections.  The status of all objects on the map
       will be reset to UNKNOWN."
    ::= 50

lnAlarmClearServers TRAP-TYPE
    ENTERPRISE Notes
    VARIABLES { lnAlarmServerHandle }
    DESCRIPTION
      "This trap is sent by NotesView for AIX to cause the
       alarm manager daemon (nvalarmgrd) to clear all alarms for a given
       server or group of servers.  The status of all the connections
       for each serverId specified in the PDU will also be cleared.
       The resulting status of all related objects on the map will
       be reset to UNKNOWN."
    ::= 51

lnSignalAutodiscoveryStart TRAP-TYPE
    ENTERPRISE Notes
    DESCRIPTION
      "This trap is sent by the NotesView for AIX console when
        the Autodiscovery process starts.  The NotesView Alarm Manager
        daemon (nvalarmgrd) will suspends all Alarm processing until
        the Autodiscovery process is complete."
    ::= 52

lnSignalAutodiscoveryFinished TRAP-TYPE
    ENTERPRISE Notes
    DESCRIPTION
      "This trap will be used by NotesView for AIX to signal the
       Alarm Manager daemon (nvalarmgrd) that the Autodiscovery process
       has completed or stopped.  Alarm processing will continue at
       this point, and all alarms that were received during Autodiscovery
       will be processed."
    ::= 53

lnSignalServerConfigChg TRAP-TYPE
    ENTERPRISE Notes
    VARIABLES {lnSignalServerId, lnSignalOldServerType,
               lnSignalNewServerType, lnSignalWhatHasChanged }
    DESCRIPTION
      "This trap will be used by NotesView for AIX to signal the
       Alarm Manager daemon (nvalarmgrd) that there has been
       a Notes server configuration change."
    ::= 54

lnTrapRequestMostSevereStatus TRAP-TYPE
    ENTERPRISE Notes
    VARIABLES { lnAlarmServerHandle }
    DESCRIPTION
        "This trap will be sent by the NotesView management station when it
         needs to be updated with the most severe status of a given object"
    ::= 55

lnTrapDisplayAlarmClearServers TRAP-TYPE
    ENTERPRISE Notes
    VARIABLES { lnSignalServerId, lnSignalServerName }
    DESCRIPTION
      "This trap will be generated by the NotesView Alarm Manager in
       order to display which server had its alarms cleared as a result
       of receiving lnAlarmClearServers (trap type 51).  One of these
       traps will be generated for each server bound in the PDU for
       the lnAlarmClearServers trap.  For display only.  The Alarm Manager
      does not do any processing for this trap."
    ::= 60

lnTrapDisplayClearedAlarm TRAP-TYPE
    ENTERPRISE Notes
    VARIABLES { lnAlarmSeverityStr, lnAlarmTypeStr,
                lnAlarmMessage, lnAlarmMessageExt }
    DESCRIPTION
      "This trap will be sent by the NotesView management station when it
       receives a clearing alarm from the poller (or console) to display the
       alarm information on the NetView event cards.  The alarms are
       configured not to be displayed in the event cards, since the PDU
       of an Alarm trap doesn't contain any information useful to
       the user.  Once the alarm is received, the PDU is deciphered and
       this informational trap is generated by the NotesView Alarm Manager."
    ::= 70

lnTrapDisplayIndeterminateAlarm TRAP-TYPE
    ENTERPRISE Notes
    VARIABLES { lnAlarmSeverityStr, lnAlarmTypeStr,
                lnAlarmMessage, lnAlarmMessageExt }
    DESCRIPTION
      "This trap will be sent by the NotesView management station when it
       receives an indeterminate alarm from the poller (or console) to
       display the alarm information on the NetView event cards.  The alarms
       are configured not to be displayed in the event cards, since the PDU
       of an Alarm trap doesn't contain any information useful to
       the user.  Once the alarm is received, the PDU is deciphered and
       this informational trap is generated by the NotesView Alarm Manager."
    ::= 71

lnTrapDisplayWarningAlarm TRAP-TYPE
    ENTERPRISE Notes
    VARIABLES { lnAlarmSeverityStr, lnAlarmTypeStr,
                lnAlarmMessage, lnAlarmMessageExt }
    DESCRIPTION
      "This trap will be sent by the NotesView management station when it
       receives a warning alarm from the poller (or console) to display the
       alarm information on the NetView event cards.  The alarms are
       configured not to be displayed on the event cards, since the PDU
       of an Alarm trap doesn't contain any information useful to
       the user.  Once the alarm is received, the PDU is deciphered and
       this informational trap is generated by the NotesView Alarm Manager."
    ::= 72

lnTrapDisplayMinorAlarm TRAP-TYPE
    ENTERPRISE Notes
    VARIABLES { lnAlarmSeverityStr, lnAlarmTypeStr,
                lnAlarmMessage, lnAlarmMessageExt }
    DESCRIPTION
      "This trap will be sent by the NotesView management station when it
       receives a minor alarm from the poller (or console) to display the
       alarm information on the NetView event cards.  The alarms are
       configured not to be displayed in the event cards, since the PDU
       of an Alarm trap doesn't contain any information useful to
       the user.  Once the alarm is received, the PDU is deciphered and
       this informational trap is generated by the NotesView Alarm Manager."
    ::= 73

lnTrapDisplayCriticalAlarm TRAP-TYPE
    ENTERPRISE Notes
    VARIABLES { lnAlarmSeverityStr, lnAlarmTypeStr,
                lnAlarmMessage, lnAlarmMessageExt }
    DESCRIPTION
      "This trap will be sent by the NotesView management station when it
       receives a critical alarm from the poller (or console) to display the
       alarm information on the NetView event cards.  The alarms are
       configured not to be displayed in the event cards, since the PDU
       of an Alarm trap doesn't contain any information useful to
       the user.  Once the alarm is received, the PDU is deciphered and
        this informational trap is generated by the NotesView Alarm Manager."
    ::= 74

lnTrapDisplayMajorAlarm TRAP-TYPE
    ENTERPRISE Notes
    VARIABLES { lnAlarmSeverityStr, lnAlarmTypeStr,
                lnAlarmMessage, lnAlarmMessageExt }
    DESCRIPTION
      "This trap will be sent by the NotesView management station when it
       receives a major alarm from the poller (or console) to display the
       alarm information on the NetView event cards.  The alarms are
       configured not to be displayed in the event cards, since the PDU
       of an Alarm trap doesn't contain any information useful to
       the user.  Once the alarm is received, the PDU is deciphered and
       this informational trap is generated by the NotesView Alarm Manager."
    ::= 75

END
